FME workspace demo_1.fmw
Description: This workspace demonstrates how to send a GraphQL query to the Danish Address Register (DAF) API, process the JSON response, and convert address point data into geometries with coordinate systems.
The workflow starts by defining a GraphQL query as an attribute. The query is formatted and wrapped as a JSON string, then sent via HTTP POST to the DAF API. The JSON response is fragmented and parsed to extract address point records, including geometry in WKT format and coordinate system information. The workspace then creates geometry from the WKT, assigns the correct coordinate system, and outputs the processed features for inspection.
Overall, the workspace automates the process of querying, parsing, and spatially enabling address data from a GraphQL API.

Parameters:
- Connection =   # DAF Connection
- DAR_ENDPOINT = https://graphql.datafordeler.dk/DAR/v1?apikey=
- DAF_API_TOKEN =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   # API Token

Junction_4
    -> DAR_ADRESSEPUNKT
DAR_ADRESSEPUNKT: Inspector

Bookmark: 1.Define GraphQL Query
Note: query { / DAR_Adressepunkt( / first: 10, / registreringstid: "2025-06-04T00:00:00Z" / virkningstid: "2025-06-04T00:00:00Z") / { / nodes { / id_lokalId / status / oprindelse_kilde / oprindelse_noejagtighedsklasse / oprindelse_tekniskStandard / position { / wkt / crs / type / dimension / } / registreringFra / virkningFra / } / } / }
Creator
    GEOMTYPE = Geometry Object
    NUM = 1
    CREATED -> AttributeCreator
AttributeCreator
    ATTR_TABLE:
      SET_TO _gql (varchar(429)) = query {
          DAR_Adressepunkt(
            first: 10,
            registreringstid: "2025-06-04T00:00:00Z"
            virkningstid:  "2025-06-04T00:00:00Z")
             {
            nodes {
              id_lokalId
              status
              oprindelse_kilde
              oprindelse_noejagtighedsklasse
              oprindelse_tekniskStandard
              position {
                wkt
                crs
                type
                dimension
              }
              registreringFra
              virkningFra
            }
          }
        }
    -> Junction_19

Bookmark: 2.GraphQL string to JSON payload (secret sauce) 🕵
Junction_19
    -> AttributeCopier_2
Note: Create _gql_rest attribute
AttributeCopier_2
    ATTR_TABLE = COPY _gql > _gql_rest
    MISSING_INPUT_ATTRS = REMOVE
    -> StringReplacer_25
Note: Replace LF with \n
StringReplacer_25
    CASE = NO
    FIND_TEXT = "\n"
    NO_MATCH = _FME_NO_OP_
    REGEXP = NO
    REPLACE_TEXT = \n
    SRC_ATTRS = _gql_rest
    -> StringReplacer_26
StringReplacer_26
    CASE = NO
    FIND_TEXT = "
    NO_MATCH = _FME_NO_OP_
    REGEXP = NO
    REPLACE_TEXT = \"
    SRC_ATTRS = _gql_rest
    -> StringConcatenator_42
StringConcatenator_42
    ACTION = Create New Attribute
    PARM_LINE:
      fme_basicstring:22%17%22:{
        "query": "        @Value(_gql_rest)",
        "variables": {}
      }
    VAL_ATTR = _gql_rest
    -> Junction_20
Note: Escape " with \"
Note: Wrap in Json query and variables
Junction_20
    -> Junction
Junction
    -> HTTPCaller

Bookmark: 3.HTTPCall
Note: Request URL (endpoint + token) / https://graphql.datafordeler.dk/DAR/v1?apikey=
Note: HTTP Method POST
Note: Upload body _gql_rest
Note: Concurrent requests: 1 is recommended. / (Depending on workflow!)
HTTPCaller
    CLIENT_CERTIFICATE_TYPE = NONE
    CONNECTION_TIMEOUT_LENGTH = 60
    CONTENT_TYPE_LOOKUP = application/json
    ERROR_ATTR = _error
    FOLLOW_REDIRECTS = FOLLOW_WITH_GET
    HTTP_METHOD = POST
    MAX_HTTP_VERSION = HTTP_2
    MAX_TRANSFERS_IN_PROGRESS = 1
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = $(DAR_ENDPOINT)$(DAF_API_TOKEN)
    TRANSFER_TIMEOUT_LENGTH = 90
    UPLOAD_BODY = @Value(_gql_rest)
    UPLOAD_TYPE = STRING_UPLOAD
    USE_COOKIES = No
    VERIFY_SSL_CERTIFICATES = Yes
    UPLOAD_CONTENT_TYPE = JSON (application/json)
    -> Junction_2
    <REJECTED> -> AttributeKeeper
Junction_2
    -> JSONFragmenter
AttributeKeeper
    CREATE_BULK_MODE_FEATURES = NO
    KEEP_ATTRS = _http_status_code,_response_body
    -> ERROR
Note: Always handle rejected / is good tone
ERROR: Inspector

Bookmark: 4.Handle Json reply
Note: Json Query json[*][*]
Note: Expose nodes{} list
JSONFragmenter
    EXPLODE_FORMAT = JSON
    EXTRACT_ATTR = Yes
    JSON_ATTR = _response_body
    JSON_QUERY = json[*][*]
    NEW_ATTRIBUTES = nodes{} buffer
    READ_FROM_FILE = NO
    RECURSIVE = YES
    REJECT_EMPTY_LISTS = YES
    FRAGMENTS -> ListExploder
Note: Explode nodes{} list to features
ListExploder
    ATTR_CONFLICT_RES_LOOKUP = INCOMING_IF_CONFLICT
    INDEX_ATTR = _element_index
    LIST_ATTR = nodes{}
    ATTR_ACCUM_MODE = Merge List Attributes
    ATTR_CONFLICT_RES = Use List Attribute Values
    ELEMENTS -> AttributeExposer
Note: Expose attributes you are interested in
AttributeExposer
    ATTR_TABLE = id_lokalId,,oprindelse_kilde,,oprindelse_noejagtighedsklasse,,oprindelse_tekniskStandard,,position.crs,,position.dimension,,position.type,,position.wkt,,registreringFra,,status,
    -> AttributeRemover
Note: Remove not needed attributes
AttributeRemover
    REMOVE_ATTRS = _creation_instance,_element_index,_gql,_gql_rest,_http_status_code,_response_body,json_index,json_type
    -> Junction_3
Junction_3
    -> AttributeCreator_2

Bookmark: 5.Coordinates and geometries
Note: Add EPSG: to get complete string
AttributeCreator_2
    ATTR_TABLE = SET_TO _crs (varchar(200)) = EPSG:@Value(position.crs)
    -> CoordinateSystemSetter
Note: Set coordinate system
CoordinateSystemSetter
    COORDSYS = @Value(_crs)
    -> GeometryReplacer
Note: Create geometry from WKT!
GeometryReplacer
    KIND = wkt
    OGC_WKT_PRECISION = FLOAT_64
    REMOVE_ATTRIBUTE = No
    SOURCE = @Value(position.wkt)
    KIND_LONG = OGC Well Known Text
    OGC_WKT_PRECISION_DISPLAY = 64-bit
    -> Junction_4

Bookmark: 0. Documentation
Note: 2025 ulf.mansson@sweco.se / Demo: How to send GraphQL query to DAF and process reply to geometries, / Use at your own risk. / You need to set user parameters: / DAF_API_TOKEN (your own token) / DAR_ENDPOINT (may need to be updated)
Note: See recorded webinar at https://dataflow.center/webinars / "#SkiftRESTud – få GraphQL-adgang till DAF med FME 2025-08-28"
Note: FME AI Assist summary: / This workspace demonstrates how to send a GraphQL query to the Danish Address Register (DAF) API, process the JSON response, and convert address point data into geometries with coordinate systems. / The workflow starts by defining a GraphQL query as an attribute. The query is formatted and wrapped as a JSON string, then sent via HTTP POST to the DAF API. The JSON response is fragmented and parsed to extract address point records, including geometry in WKT format and coordinate system information. The workspace then creates geometry from the WKT, assigns the correct coordinate system, and outputs the processed features for inspection. / Overall, the workspace automates the process of querying, parsing, and spatially enabling address data from a GraphQL API.
