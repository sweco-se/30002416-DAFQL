FME workspace demo_2.fmw
Description: This workspace demonstrates how to send a GraphQL query to the Danish Address Register (DAF) API, process the JSON response, and convert address point data into geometries with coordinate systems.
The workflow starts by defining a GraphQL query as an attribute. The query is formatted and wrapped as a JSON string, then sent via HTTP POST to the DAF API. The JSON response is fragmented and parsed to extract address point records, including geometry in WKT format and coordinate system information. The workspace then creates geometry from the WKT, assigns the correct coordinate system, and outputs the processed features for inspection.
Overall, the workspace automates the process of querying, parsing, and spatially enabling address data from a GraphQL API.

Parameters:
- Connection =   # DAF Connection
- DAR_ENDPOINT = https://graphql.datafordeler.dk/DAR/v1?apikey=
- DAF_API_TOKEN =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   # API Token
- PAGESIZE = 10   # Page Size

Junction_3
    -> Junction
Junction_2
    -> Junction
Junction
    -> ListExploder
DAR_NavngivenVej: Inspector

Bookmark: 1.Define GraphQL Query
Note: query { / DAR_NavngivenVej( / where: { / vejnavnebeliggenhed_vejnavnelinje: { / within: { / wkt: "POLYGON ((552226.3409 6320342.4921,552226.3409 6327161.1958,560167.2802 6327161.1958,560167.2802 6320342.4921,552226.3409 6320342.4921))" / crs: 25832 / } / } / } / first: 200 / registreringstid: "2025-08-26T00:00:00Z" / virkningstid: "2025-08-26T00:00:00Z" / ){ / pageInfo { / endCursor / hasNextPage / } / nodes { / beskrivelse / id_lokalId / vejnavn / vejnavnebeliggenhed_vejnavnelinje { / wkt / crs / } / status / } / } / }
Creator
    GEOMTYPE = Geometry Object
    NUM = 1
    CREATED -> AttributeCreator
AttributeCreator
    ATTR_TABLE:
      SET_TO _gql (varchar(550)) = query {
        	DAR_NavngivenVej(
        		where: {
        						vejnavnebeliggenhed_vejnavnelinje: {
        				within: {
        					wkt: "POLYGON ((552226.3409 6320342.4921,552226.3409 6327161.1958,560167.2802 6327161.1958,560167.2802 6320342.4921,552226.3409 6320342.4921))"
        					crs: 25832
        				}
        			}
        		}
        		first: 200
        		registreringstid: "2025-08-26T00:00:00Z"
        		virkningstid:  "2025-08-26T00:00:00Z"
        	){
        		pageInfo {
        			endCursor
        			hasNextPage
        		}
        		nodes {
        			beskrivelse
        			id_lokalId
        			vejnavn
        			vejnavnebeliggenhed_vejnavnelinje {
        				wkt
        				crs
        			}
        			status
        		}
         	}
        }
    -> GraphQLtoJSON

Bookmark: 2. First call to get first records and possible cursor for following pages
GraphQLtoJSON
    GQL = @Value(_gql)
    -> HTTPCaller
HTTPCaller
    CLIENT_CERTIFICATE_TYPE = NONE
    CONNECTION_TIMEOUT_LENGTH = 60
    CONTENT_TYPE_LOOKUP = application/json
    ERROR_ATTR = _error
    FOLLOW_REDIRECTS = FOLLOW_WITH_GET
    HTTP_METHOD = POST
    MAX_HTTP_VERSION = HTTP_2
    MAX_TRANSFERS_IN_PROGRESS = 1
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = $(DAR_ENDPOINT)$(DAF_API_TOKEN)
    TRANSFER_TIMEOUT_LENGTH = 90
    UPLOAD_BODY = @Value(_gql_rest)
    UPLOAD_TYPE = STRING_UPLOAD
    USE_COOKIES = No
    VERIFY_SSL_CERTIFICATES = Yes
    UPLOAD_CONTENT_TYPE = JSON (application/json)
    -> JSONFragmenter
Note: Expose: / pageInfo.endCursor / pageInfo.hasNextPage
JSONFragmenter
    EXPLODE_FORMAT = JSON
    EXTRACT_ATTR = Yes
    JSON_ATTR = _response_body
    JSON_QUERY = json[*][*]
    NEW_ATTRIBUTES = nodes{} buffer pageInfo.endCursor buffer pageInfo.hasNextPage buffer
    READ_FROM_FILE = NO
    RECURSIVE = YES
    REJECT_EMPTY_LISTS = YES
    FRAGMENTS -> Tester
Note: Is there a next page?
Tester
    BOOL_OP = OR
    TEST_CLAUSE = TEST @Value(pageInfo.hasNextPage) = Yes
    TEST_MODE = TEST
    PASSED -> VariableSetter
    PASSED -> Junction_3
    FAILED -> Junction_3

Bookmark: 3. Set up global variable and clone max number of calls. Secret sauce.
Note: Global variable vEndCursor / has the next cursor
VariableSetter
    SCOPE = Global
    VALUE = @Value(pageInfo.endCursor)
    VARNAME = vEndCursor
    -> Cloner
Note: Max 20 calls. / Possibly 4000 records
Cloner
    COPIES = 20
    COPYATT = _copynum
    COPY -> VariableRetriever
Note: Look ahead for new cursor in global variable
VariableRetriever
    SCOPE = Global
    VALUE_ATTR = _v_cursor
    VARNAME = vEndCursor
    -> Tester_9
Note: Last page?
Tester_9
    BOOL_OP = OR
    TEST_CLAUSE = TEST @Value(_v_cursor) != lastpage
    TEST_MODE = TEST
    PASSED -> AttributeCreator_2

Bookmark: 4. Prepare modified GraphQL by inserting cursor for consecutive calls
Note: query { / DAR_NavngivenVej( / where: { / vejnavnebeliggenhed_vejnavnelinje: { / within: { / wkt: "POLYGON ((552226.3409 6320342.4921,552226.3409 6327161.1958,560167.2802 6327161.1958,560167.2802 6320342.4921,552226.3409 6320342.4921))" / crs: 25832 / } / } / } / first: 200 / after: <pageInfo.endCursor> / registreringstid: "2025-08-26T00:00:00Z" / virkningstid: "2025-08-26T00:00:00Z" / ){ / pageInfo { / endCursor / hasNextPage / } / nodes { / beskrivelse / id_lokalId / vejnavn / vejnavnebeliggenhed_vejnavnelinje { / wkt / crs / } / status / } / } / }
AttributeCreator_2
    ATTR_TABLE:
      SET_TO _gql (buffer) = query {
        	DAR_NavngivenVej(
        		where: {
        						vejnavnebeliggenhed_vejnavnelinje: {
        				within: {
        					wkt: "POLYGON ((552226.3409 6320342.4921,552226.3409 6327161.1958,560167.2802 6327161.1958,560167.2802 6320342.4921,552226.3409 6320342.4921))"
        					crs: 25832
        				}
        			}
        		}
        		first: 200
        		after: "<pageInfo.endCursor>"
        		registreringstid: "2025-08-26T00:00:00Z"
        		virkningstid:  "2025-08-26T00:00:00Z"
        	){
        		pageInfo {
        			endCursor
        			hasNextPage
        		}
        		nodes {
        			beskrivelse
        			id_lokalId
        			vejnavn
        			vejnavnebeliggenhed_vejnavnelinje {
        				wkt
        				crs
        			}
        			status
        		}
         	}
        }
    -> StringReplacer_29
StringReplacer_29
    CASE = NO
    FIND_TEXT = <pageInfo.endCursor>
    NO_MATCH = _FME_NO_OP_
    REGEXP = NO
    REPLACE_TEXT = @Value(_v_cursor)
    SRC_ATTRS = _gql
    -> GraphQLtoJSON_2
GraphQLtoJSON_2
    GQL = @Value(_gql)
    -> AttributeRemover
AttributeRemover
    LIST_ATTRS = nodes{}
    -> HTTPCaller_2

Bookmark: 5. Consecutive calls with different cursors. Secret sauce variable-handling.
HTTPCaller_2
    CLIENT_CERTIFICATE_TYPE = NONE
    CONNECTION_TIMEOUT_LENGTH = 60
    CONTENT_TYPE_LOOKUP = application/json
    ERROR_ATTR = _error
    FOLLOW_REDIRECTS = FOLLOW_WITH_GET
    HTTP_METHOD = POST
    MAX_HTTP_VERSION = HTTP_2
    MAX_TRANSFERS_IN_PROGRESS = 1
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = $(DAR_ENDPOINT)$(DAF_API_TOKEN)
    TRANSFER_TIMEOUT_LENGTH = 90
    UPLOAD_BODY = @Value(_gql_rest)
    UPLOAD_TYPE = STRING_UPLOAD
    USE_COOKIES = No
    VERIFY_SSL_CERTIFICATES = Yes
    UPLOAD_CONTENT_TYPE = JSON (application/json)
    -> JSONFragmenter_2
JSONFragmenter_2
    EXPLODE_FORMAT = JSON
    EXTRACT_ATTR = Yes
    JSON_ATTR = _response_body
    JSON_QUERY = json[*][*]
    NEW_ATTRIBUTES = nodes{} buffer pageInfo.endCursor buffer pageInfo.hasNextPage buffer
    READ_FROM_FILE = NO
    RECURSIVE = YES
    REJECT_EMPTY_LISTS = YES
    FRAGMENTS -> Tester_8
Tester_8
    BOOL_OP = OR
    TEST_CLAUSE = TEST @Value(pageInfo.hasNextPage) = Yes
    TEST_MODE = TEST
    PASSED -> VariableSetter_2
    FAILED -> VariableSetter_3
VariableSetter_2
    SCOPE = Global
    VALUE = @Value(pageInfo.endCursor)
    VARNAME = vEndCursor
    -> Junction_2
VariableSetter_3
    SCOPE = Global
    VALUE = lastpage
    VARNAME = vEndCursor
    -> Junction_2

Bookmark: 6. Get all records in all nodes-lists
ListExploder
    ATTR_CONFLICT_RES_LOOKUP = INCOMING_IF_CONFLICT
    INDEX_ATTR = _element_index
    LIST_ATTR = nodes{}
    ATTR_ACCUM_MODE = Merge List Attributes
    ATTR_CONFLICT_RES = Use List Attribute Values
    ELEMENTS -> AttributeExposer
AttributeExposer
    ATTR_TABLE = beskrivelse,,id_lokalId,,status,,vejnavn,,vejnavnebeliggenhed_vejnavnelinje.crs,,vejnavnebeliggenhed_vejnavnelinje.wkt,
    -> AttributeKeeper
AttributeKeeper
    CREATE_BULK_MODE_FEATURES = NO
    KEEP_ATTRS = beskrivelse,id_lokalId,status,vejnavn,vejnavnebeliggenhed_vejnavnelinje.crs,vejnavnebeliggenhed_vejnavnelinje.wkt
    -> AttributeCreator_3

Bookmark: 7.Coordinates and geometries
Note: Add EPSG: to get complete string
AttributeCreator_3
    ATTR_TABLE = SET_TO _crs (varchar(200)) = EPSG:@Value(vejnavnebeliggenhed_vejnavnelinje.crs)
    -> CoordinateSystemSetter
Note: Set coordinate system
CoordinateSystemSetter
    COORDSYS = @Value(_crs)
    -> GeometryReplacer
Note: Create geometry from WKT!
GeometryReplacer
    KIND = wkt
    OGC_WKT_PRECISION = FLOAT_64
    REMOVE_ATTRIBUTE = No
    SOURCE = @Value(vejnavnebeliggenhed_vejnavnelinje.wkt)
    KIND_LONG = OGC Well Known Text
    OGC_WKT_PRECISION_DISPLAY = 64-bit
    -> Junction_4
Junction_4
    -> DAR_NavngivenVej

Bookmark: 0. Documentation
Note: 2025 ulf.mansson@sweco.se / Demo of: / 1.Using where clause with geometry / 2. Make consecutive calls to get complete sets / 3. Using Global Variables: / -HTTP Callers should not make simultaneous calls. / -Variables are runtime => Can give unexpected results while developing and using feature caching. So execute from beginning to be sure. / Alternative solutions: / -Custom Transformer Looping / -FME Flow Automations Looping / -PythonCaller or Python Package
Note: Use at your own risk. / You need to set user parameters: / DAF_API_TOKEN (your own token) / DAR_ENDPOINT (may need to be updated)
Note: See recorded webinar at https://dataflow.center/webinars / "#SkiftRESTud – få GraphQL-adgang till DAF med FME 2025-08-28"
Note: FME AI Assist Summary / This workspace automates the retrieval of address data from the Danish Address Register (DAF) using a GraphQL API. It builds a GraphQL query, formats it for REST, and sends it via HTTP POST. The JSON response is parsed to extract address records, including geometry in WKT format and coordinate system info. The workspace then creates spatial features from the WKT, sets the correct coordinate system, and outputs the results for inspection. / It also handles pagination by using cursors to make consecutive API calls, ensuring all records are retrieved.

FME custom transformer GraphQLtoJSON

Parameters:
- GQL =   # GraphQL

Input (input)
    -> Junction_19
Output (output)

Bookmark: 2.GraphQL string to JSON payload (secret sauce) 🕵
Junction_19
    -> ParameterFetcher
Note: Create _gql_rest attribute
ParameterFetcher
    ATTR_LIST = _gql $(GQL) _gql_rest $(GQL)
    -> StringReplacer
Note: Replace LF with \n
StringReplacer
    CASE = NO
    FIND_TEXT = "\n"
    NO_MATCH = _FME_NO_OP_
    REGEXP = NO
    REPLACE_TEXT = \n
    SRC_ATTRS = _gql_rest
    -> StringReplacer_2
StringReplacer_2
    CASE = NO
    FIND_TEXT = "
    NO_MATCH = _FME_NO_OP_
    REGEXP = NO
    REPLACE_TEXT = \"
    SRC_ATTRS = _gql_rest
    -> StringConcatenator
StringConcatenator
    ACTION = Create New Attribute
    PARM_LINE:
      fme_basicstring:22%17%22:{
        "query": "        @Value(_gql_rest)",
        "variables": {}
      }
    VAL_ATTR = _gql_rest
    -> Junction_20
Note: Escape " with \"
Note: Wrap in Json query and variables
Junction_20
    -> Junction
Junction
    -> Output (output)
