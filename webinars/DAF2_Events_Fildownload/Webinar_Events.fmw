FME workspace Webinar_Events.fmw

Parameters:
- Entitet = Bygning
- HOURS = 2   # Timer siden

JSONFragmenter_3
    EXPLODE_FORMAT = JSON
    EXTRACT_ATTR = Yes
    JSON_ATTR = _response_body
    JSON_QUERY = json[*][*]
    NEW_ATTRIBUTES = nodes{} buffer pageInfo.endCursor buffer pageInfo.hasNextPage buffer
    READ_FROM_FILE = NO
    RECURSIVE = YES
    REJECT_EMPTY_LISTS = YES
    FRAGMENTS -> Tester
    <REJECTED> -> Junction
Note: Is there a next page?
Tester
    BOOL_OP = OR
    TEST_CLAUSE = TEST @Value(pageInfo.hasNextPage) = Yes
    TEST_MODE = TEST
    PASSED -> VariableSetter
    PASSED -> Junction_9
    FAILED -> Junction_9
Junction_9
    -> Junction_8
Junction_11
    -> Junction_8
Junction_8
    -> JSONFragmenter_5
JSONFragmenter_6
    EXPLODE_FORMAT = JSON
    EXTRACT_ATTR = Yes
    JSON_ATTR = _response_body
    JSON_QUERY = json["data"]["BBR_Bygning"]["nodes"][*]
    NEW_ATTRIBUTES = id_lokalId buffer datafordelerOpdateringstid buffer entityname buffer eventaction buffer object_id buffer object_status buffer byg404Koordinat.wkt buffer byg404Koordinat.crs buffer
    READ_FROM_FILE = NO
    RECURSIVE = YES
    REJECT_EMPTY_LISTS = YES
    FRAGMENTS -> Tester_4
    <REJECTED> -> AttributeCreator_13
Tester_4
    BOOL_OP = OR
    TEST_CLAUSE = TEST byg404Koordinat.crs ATTRIBUTE_HAS_A_VALUE ""
    TEST_MODE = TEST
    PASSED -> GeometryReplacer
    FAILED -> Junction_3
GeometryReplacer
    KIND = wkt
    OGC_WKT_PRECISION = FLOAT_64
    REMOVE_ATTRIBUTE = Yes
    SOURCE = @Value(byg404Koordinat.wkt)
    KIND_LONG = OGC Well Known Text
    OGC_WKT_PRECISION_DISPLAY = 64-bit
    -> AttributeCreator_12
AttributeCreator_12
    ATTR_TABLE = SET_TO byg404Koordinat.crs (buffer) = EPSG:@Value(byg404Koordinat.crs)
    INPUT_PORT_CONNECTED = CONNECTED
    -> CoordinateSystemSetter
CoordinateSystemSetter
    COORDSYS = @Value(byg404Koordinat.crs)
    -> Opdaterade_bygninger
Opdaterade_bygninger: Inspector
Note: Bygninger uden geometri
Junction_3
Note: JSONFragmenter_2 : rejected
Junction_7
    -> Junction
Junction
    -> Junction_2
Junction_2
    -> AttributeCreator_13
Note: HTTPCaller_2 : <Rejected>
Junction_5
    -> AttributeCreator_11
Creator_5
    GEOMTYPE = Geometry Object
    NUM = 1
    CREATED -> AttributeCreator_14

Bookmark: Fetch BBR_Events
Creator
    GEOMTYPE = Geometry Object
    NUM = 1
    CREATED -> DateTimeStamper
DateTimeStamper
    DATETIME_ATTR = _timestamp
    INCLUDE_FRAC_SECONDS = YES
    INCLUDE_OFFSET = NO
    SCOPE = translation
    STAMP_TYPE = datetime
    TIMEZONE = utc
    -> DateTimeCalculator
DateTimeCalculator
    DAYS = 0
    HOURS = $(HOURS)
    MINUTES = 0
    MODE = DATETIMECALC_1_ADD_INTERVAL
    MONTHS = 0
    OPERATION_PARAMETERS = START_DATETIME_DATETIMECALC_1_ADD_INTERVAL]@Value(_timestamp)]OPERATOR]SUBTRACT]YEARS]0]MONTHS]0]DAYS]0]HOURS]$(HOURS)]MINUTES]0]SECONDS]0]RESULT_DATETIME]_result_datetime]START_DATETIME]@Value(_timestamp)
    OPERATOR = SUBTRACT
    RESULT_DATETIME = _result_datetime
    SECONDS = 0
    START_DATETIME = @Value(_timestamp)
    START_DATETIME_DATETIMECALC_1_ADD_INTERVAL = @Value(_timestamp)
    YEARS = 0
    -> AttributeCreator_5
AttributeCreator_5
    ATTR_TABLE:
      SET_TO query.Opdateringstid (varchar(200)) = FME_CONDITIONAL:DEFAULT_VALUE'FME_NULL_VALUE'BOOL_OP;OR;COMPOSITE_TEST;1;TEST query.Opdateringstid NOT_ATTRIBUTE_HAS_A_VALUE _FME_BLANK_STRING_'@DateTimeFormat(@Value(_result_datetime),%Y-%m-%dT%H:%M:%SZ)'FME_NUM_CONDITIONS2___
      SET_TO _oneWeekAgo (varchar(200)) = @DateTimeAdd(@DateTimeNow(),-P1D)
      SET_TO query.entitet (varchar(200)) = $(Entitet)
    -> AttributeCreator_2
Note: Create query
AttributeCreator_2
    ATTR_TABLE:
      SET_TO _gql (varchar(200)) = query {
            BBR_Events(
                where: {
                    and: [
                        { entityname: { eq: "@Value(query.entitet)" } }
                        { datafordelerOpdateringstid: { gte: "@Value(query.Opdateringstid)"} }
                    ]
                }
                first: 1000
            ) {
                pageInfo {
                    hasNextPage
                    endCursor
                 }
                nodes {
                    eventid
                    entityname
                    eventaction
                    object_id
                    object_status
                    object_datafordelerRowId
                    object_datafordelerRowVersion
                    object_registreringfra
                    object_registreringtil
                    object_virkningfra
                    object_virkningtil
                    datafordelerOpdateringstid
                }
            }
        }
    -> StringReplacer_4
StringReplacer_4
    CASE = NO
    FIND_TEXT = virkningstid: "",<pipe>registreringstid: ""
    NO_MATCH = _FME_NO_OP_
    REGEXP = YES
    SRC_ATTRS = _gql
    -> AttributeCopier_3
AttributeCopier_3
    ATTR_TABLE = COPY _gql > _gql_rest
    MISSING_INPUT_ATTRS = REMOVE
    -> StringReplacer_2
StringReplacer_2
    CASE = NO
    FIND_TEXT = "\n"
    NO_MATCH = _FME_NO_OP_
    REGEXP = NO
    REPLACE_TEXT = \n
    SRC_ATTRS = _gql_rest
    -> StringReplacer_3
StringReplacer_3
    CASE = NO
    FIND_TEXT = "
    NO_MATCH = _FME_NO_OP_
    REGEXP = NO
    REPLACE_TEXT = \"
    SRC_ATTRS = _gql_rest
    -> StringConcatenator_2
StringConcatenator_2
    ACTION = Create New Attribute
    PARM_LINE:
      fme_basicstring:22%17%22:{
        "query": "        @Value(_gql_rest)",
        "variables": {}
      }
    VAL_ATTR = _gql_rest
    -> HTTPCaller_3
HTTPCaller_3
    AUTH_METHOD_TYPE = NC
    AUTH_NAMED_CONNECTION = DAF GraphQL API Key v1
    CLIENT_CERTIFICATE_TYPE = NONE
    CONNECTION_TIMEOUT_LENGTH = 60
    CONTENT_TYPE_LOOKUP = application/json
    ERROR_ATTR = _error
    FOLLOW_REDIRECTS = FOLLOW_WITH_GET
    HTTP_METHOD = POST
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://graphql.datafordeler.dk/BBR/v1/
    TRANSFER_TIMEOUT_LENGTH = 90
    UPLOAD_BODY = @Value(_gql_rest)
    UPLOAD_TYPE = STRING_UPLOAD
    USE_COOKIES = No
    VERIFY_SSL_CERTIFICATES = Yes
    AUTH_METHOD = Web Connection
    UPLOAD_CONTENT_TYPE = JSON (application/json)
    -> JSONFragmenter_3

Bookmark: 3. Set up global variable and clone max number of calls. Secret sauce.
Note: Global variable vEndCursor / has the next cursor
VariableSetter
    SCOPE = Global
    VALUE = @Value(pageInfo.endCursor)
    VARNAME = vEndCursor
    -> Cloner
Note: Max 19 calls here => 20 total. / Possibly 4000 records
Cloner
    COPIES = 19
    COPYATT = _copynum
    COPY -> VariableRetriever
Note: Look ahead for new cursor in global variable
VariableRetriever
    SCOPE = Global
    VALUE_ATTR = _v_cursor
    VARNAME = vEndCursor
    -> Tester_9
    <REJECTED> -> Junction
Note: Last page?
Tester_9
    BOOL_OP = OR
    TEST_CLAUSE = TEST @Value(_v_cursor) != lastpage
    TEST_MODE = TEST
    PASSED -> StringReplacer

Bookmark: 4. Prepare modified GraphQL by inserting cursor for consecutive calls
Note: Add and replace next page position in query
StringReplacer
    CASE = NO
    NO_MATCH = _FME_NO_OP_
    REGEXP = YES
    STR_REPLACE_TABLE:
      _gql ([ \t]*)first: (\d*) \1first: \2
      \1after: "@Value(_v_cursor)"
    -> GraphQLtoJSON_2
GraphQLtoJSON_2
    GQL = @Value(_gql)
    -> AttributeRemover_3
AttributeRemover_3
    LIST_ATTRS = nodes{}
    -> HTTPCaller_4

Bookmark: 5. Consecutive calls with different cursors. Secret sauce variable-handling.
Note: Fetch sub-sequent pages of query results
HTTPCaller_4
    AUTH_METHOD_TYPE = NC
    AUTH_NAMED_CONNECTION = DAF GraphQL API Key v1
    CLIENT_CERTIFICATE_TYPE = NONE
    CONNECTION_TIMEOUT_LENGTH = 60
    CONTENT_TYPE_LOOKUP = application/json
    ERROR_ATTR = _error
    FOLLOW_REDIRECTS = FOLLOW_WITH_GET
    HTTP_METHOD = POST
    MAX_HTTP_VERSION = HTTP_2
    MAX_TRANSFERS_IN_PROGRESS = 1
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://graphql.datafordeler.dk/BBR/v1/
    TRANSFER_TIMEOUT_LENGTH = 90
    UPLOAD_BODY = @Value(_gql_rest)
    UPLOAD_TYPE = STRING_UPLOAD
    USE_COOKIES = No
    VERIFY_SSL_CERTIFICATES = Yes
    AUTH_METHOD = Web Connection
    UPLOAD_CONTENT_TYPE = JSON (application/json)
    -> JSONFragmenter_2
    <REJECTED> -> Junction_4
JSONFragmenter_2
    EXPLODE_FORMAT = JSON
    EXTRACT_ATTR = Yes
    JSON_ATTR = _response_body
    JSON_QUERY = json[*][*]
    NEW_ATTRIBUTES = nodes{} buffer pageInfo.endCursor buffer pageInfo.hasNextPage buffer
    READ_FROM_FILE = NO
    RECURSIVE = YES
    REJECT_EMPTY_LISTS = YES
    FRAGMENTS -> Tester_8
    <REJECTED> -> Junction_6
Tester_8
    BOOL_OP = AND
    TEST_CLAUSE:
      TEST @Value(pageInfo.hasNextPage) = Yes
      TEST pageInfo.endCursor ATTRIBUTE_HAS_A_VALUE ""
    TEST_MODE = TEST
    PASSED -> VariableSetter_2
    FAILED -> VariableSetter_3
VariableSetter_2
    SCOPE = Global
    VALUE = @Value(pageInfo.endCursor)
    VARNAME = vEndCursor
    -> Junction_11
VariableSetter_3
    SCOPE = Global
    VALUE = lastpage
    VARNAME = vEndCursor
    -> Junction_11
Note: To: error logging
Junction_6
    -> Junction_7
Note: AttributeCreator_11 : to error logging
Junction_4
    -> Junction_5

Bookmark: 6. Get all Event records in all nodes-lists
JSONFragmenter_5
    EXPLODE_FORMAT = JSON
    EXTRACT_ATTR = Yes
    JSON_ATTR = _response_body
    JSON_QUERY = json["nodes"][*]
    NEW_ATTRIBUTES = id_lokalId buffer datafordelerOpdateringstid buffer entityname buffer eventaction buffer eventid buffer object_id buffer object_status buffer object_datafordelerRowId buffer object_datafordelerRowVersion buffer object_registreringfra buffer object_registreringtil buffer object_virkningfra buffer object_virkningtil buffer
    READ_FROM_FILE = NO
    RECURSIVE = YES
    REJECT_EMPTY_LISTS = YES
    FRAGMENTS -> AttributeRemover
    <REJECTED> -> Junction_2
AttributeRemover
    LIST_ATTRS = nodes{}
    REMOVE_ATTRS = _copynum,_creation_instance,_gql,_gql_rest,_result_datetime,_v_cursor,json_index,json_type,pageInfo.endCursor,pageInfo.hasNextPage,query.RegistreringFra,query.VirkningFra
    -> Sorter
Note: Sort on row version for habilitating grouping on that
Sorter
    SORT_PARM = object_datafordelerRowVersion NATURAL ASCENDING NON_VALUES_AFTER_VALUES
    SORTED -> Counter

Bookmark: Fetch objects reported through BBR_Events from BBR
Note: Split count on row version number
Counter
    CNT_ATTR = groupId
    DOMAIN = @Value(object_datafordelerRowVersion)
    SCOPE = Global
    START = 0
    -> AttributeCreator_4
AttributeCreator_4
    ATTR_TABLE:
      SET_TO object_datafordelerRowId (buffer) = "@Value(object_datafordelerRowId)"
      SET_TO groupId (real64) = @Evaluate(@floor(@Value(groupId)/50,0))
    INPUT_PORT_CONNECTED = CONNECTED
    -> Aggregator_2
Note: Aggregate on group and row version
Aggregator_2
    ACCUM_ATTRS = All
    AGGREGATE_TYPE = Homogeneous Collection (If Possible)
    CONCAT_ATTRS = object_datafordelerRowId
    GROUP_BY = groupId object_datafordelerRowVersion
    MODE = Geometry - Assemble One Level
    SEP = ,
    AGGREGATE -> AttributeCreator_3
Note: Create query
AttributeCreator_3
    ATTR_TABLE:
      SET_TO _gql (varchar(200)) = query {
            BBR_Bygning(
                first: 200
                where: {
                    and: [
                        { datafordelerRowId : { in: [@Value(object_datafordelerRowId)] } }
                        { datafordelerRowVersion: { eq: @Value(object_datafordelerRowVersion) } }
                    ]
                }
            ) {
            pageInfo {
              endCursor
              hasNextPage
            }
                nodes {
                    byg007Bygningsnummer
                    byg021BygningensAnvendelse
                    byg024AntalLejlighederMedKoekken
                    byg025AntalLejlighederUdenKoekken
                    byg026Opfoerelsesaar
                    byg027OmTilbygningsaar
                    byg029DatoForMidlertidigOpfoertBygning
                    byg030Vandforsyning
                    byg031Afloebsforhold
                    byg032YdervaeggensMateriale
                    byg033Tagdaekningsmateriale
                    byg034SupplerendeYdervaeggensMateriale
                    byg035SupplerendeTagdaekningsMateriale
                    byg036AsbestholdigtMateriale
                    byg037KildeTilBygningensMaterialer
                    byg038SamletBygningsareal
                    byg039BygningensSamledeBoligAreal
                    byg040BygningensSamledeErhvervsAreal
                    byg041BebyggetAreal
                    byg042ArealIndbyggetGarage
                    byg043ArealIndbyggetCarport
                    byg044ArealIndbyggetUdhus
                    byg045ArealIndbyggetUdestueEllerLign
                    byg046SamletArealAfLukkedeOverdaekningerPaaBygningen
                    byg047ArealAfAffaldsrumITerraenniveau
                    byg048AndetAreal
                    byg049ArealAfOverdaekketAreal
                    byg050ArealAabneOverdaekningerPaaBygningenSamlet
                    byg051Adgangsareal
                    byg052BeregningsprincipCarportAreal
                    byg053BygningsarealerKilde
                    byg054AntalEtager
                    byg055AfvigendeEtager
                    byg056Varmeinstallation
                    byg057Opvarmningsmiddel
                    byg058SupplerendeVarme
                    byg069Sikringsrumpladser
                    byg070Fredning
                    byg071BevaringsvaerdighedReference
                    byg094Revisionsdato
                    byg111StormraadetsOversvoemmelsesSelvrisiko
                    byg112DatoForRegistreringFraStormraadet
                    byg113Byggeskadeforsikringsselskab
                    byg114DatoForByggeskadeforsikring
                    byg119Udledningstilladelse
                    byg121OmfattetAfByggeskadeforsikring
                    byg122Gyldighedsdato
                    byg123MedlemskabAfSpildevandsforsyning
                    byg124PaabudVedrSpildevandsafledning
                    byg125FristVedrSpildevandsafledning
                    byg126TilladelseTilUdtraeden
                    byg127DatoForTilladelseTilUdtraeden
                    byg128TilladelseTilAlternativBortskaffelseEllerAfledning
                    byg129DatoForTilladelseTilAlternativBortskaffelseEllerAfledning
                    byg130ArealAfUdvendigEfterisolering
                    byg131DispensationFritagelseIftKollektivVarmeforsyning
                    byg132DatoForDispensationFritagelseIftKollektivVarmeforsyning
                    byg133KildeTilKoordinatsaet
                    byg134KvalitetAfKoordinatsaet
                    byg135SupplerendeOplysningOmKoordinatsaet
                    byg136PlaceringPaaSoeterritorie
                    byg137BanedanmarkBygvaerksnummer
                    byg140ServitutForUdlejningsEjendomDato
                    byg150Gulvbelaegning
                    byg151Frihoejde
                    byg152AabenLukketKonstruktion
                    byg153Konstruktionsforhold
                    byg301TypeAfFlytning
                    byg302Tilflytterkommune
                    byg403OevrigeBemaerkningerFraStormraadet
                    byg404Koordinat {
                        crs
                        wkt
                    }
                    byg406Koordinatsystem
                    byg500Notatlinjer
                    datafordelerOpdateringstid
                    datafordelerRegisterImportSequenceNumber
                    datafordelerRowId
                    datafordelerRowVersion
                    ejerlejlighed
                    forretningshaendelse
                    forretningsomraade
                    forretningsproces
                    grund
                    husnummer
                    id_lokalId
                    id_namespace
                    jordstykke
                    kommunekode
                    registreringFra
                    registreringsaktoer
                    registreringTil
                    status
                    virkningFra
                    virkningsaktoer
                    virkningTil
                }
            }
        }
    -> StringReplacer_7
StringReplacer_7
    CASE = NO
    FIND_TEXT = virkningstid: "",<pipe>registreringstid: ""
    NO_MATCH = _FME_NO_OP_
    REGEXP = YES
    SRC_ATTRS = _gql
    -> AttributeCopier_2
AttributeCopier_2
    ATTR_TABLE = COPY _gql > _gql_rest
    MISSING_INPUT_ATTRS = REMOVE
    -> StringReplacer_5
StringReplacer_5
    CASE = NO
    FIND_TEXT = "\n"
    NO_MATCH = _FME_NO_OP_
    REGEXP = NO
    REPLACE_TEXT = \n
    SRC_ATTRS = _gql_rest
    -> StringReplacer_6
StringReplacer_6
    CASE = NO
    FIND_TEXT = "
    NO_MATCH = _FME_NO_OP_
    REGEXP = NO
    REPLACE_TEXT = \"
    SRC_ATTRS = _gql_rest
    -> StringConcatenator_3
StringConcatenator_3
    ACTION = Create New Attribute
    PARM_LINE:
      fme_basicstring:22%17%22:{
        "query": "        @Value(_gql_rest)",
        "variables": {}
      }
    VAL_ATTR = _gql_rest
    -> HTTPCaller_2
Note: Fetch actual changed objects
HTTPCaller_2
    AUTH_METHOD_TYPE = NC
    AUTH_NAMED_CONNECTION = DAF GraphQL API Key v1
    CLIENT_CERTIFICATE_TYPE = NONE
    CONNECTION_TIMEOUT_LENGTH = 60
    CONTENT_TYPE_LOOKUP = application/json
    ERROR_ATTR = _error
    FOLLOW_REDIRECTS = FOLLOW_WITH_GET
    HTTP_METHOD = POST
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://graphql.datafordeler.dk/BBR/v1/
    TRANSFER_TIMEOUT_LENGTH = 90
    UPLOAD_BODY = @Value(_gql_rest)
    UPLOAD_TYPE = STRING_UPLOAD
    USE_COOKIES = No
    VERIFY_SSL_CERTIFICATES = Yes
    AUTH_METHOD = Web Connection
    UPLOAD_CONTENT_TYPE = JSON (application/json)
    -> AttributeKeeper
    <REJECTED> -> AttributeCreator_11
AttributeKeeper
    CREATE_BULK_MODE_FEATURES = NO
    KEEP_ATTRS = _response_body,_timestamp,entityname,eventaction,eventid,object_id,object_status
    -> JSONFragmenter_6

Bookmark: Error logging
AttributeCreator_13
    ATTR_TABLE:
      SET_TO response.body.content_type (varchar(16)) = application/json
      SET_TO response.status_code (uint16) = 500; @Value(fme_rejection_code)
      SET_TO response.body.content (varchar(200)) = @Value(_response_body)
    -> Logger
AttributeCreator_11
    ATTR_TABLE:
      SET_TO response.body.content_type (varchar(16)) = application/json
      SET_TO response.status_code (uint16) = 500
      SET_TO response.body.content (varchar(200)) = @Value(_response_body)
    -> Logger
Logger
    LOG_FEATURE = LOG_ONLY
    MAXCOORDS = 20
    MAXFEATS = 20
    MESSAGE = Feature is:
    SEVERITY = INFO

Bookmark: Get RegisterImportStatus
Note: DAF_RegisterImportStatus for BBR
AttributeCreator_14
    ATTR_TABLE:
      SET_TO _gql (varchar(548)) = query {
            DAF_RegisterImportStatus {
                lastSequenceNumber,
                lastEventId,
                lastUpdated
            }
        }
    -> StringReplacer_19
StringReplacer_19
    CASE = NO
    FIND_TEXT = virkningstid: "",<pipe>registreringstid: ""
    NO_MATCH = _FME_NO_OP_
    REGEXP = YES
    SRC_ATTRS = _gql
    -> AttributeCopier_7
AttributeCopier_7
    ATTR_TABLE = COPY _gql > _gql_rest
    MISSING_INPUT_ATTRS = REMOVE
    -> StringReplacer_17
StringReplacer_17
    CASE = NO
    FIND_TEXT = "\n"
    NO_MATCH = _FME_NO_OP_
    REGEXP = NO
    REPLACE_TEXT = \n
    SRC_ATTRS = _gql_rest
    -> StringReplacer_18
StringReplacer_18
    CASE = NO
    FIND_TEXT = "
    NO_MATCH = _FME_NO_OP_
    REGEXP = NO
    REPLACE_TEXT = \"
    SRC_ATTRS = _gql_rest
    -> StringConcatenator_7
StringConcatenator_7
    ACTION = Create New Attribute
    PARM_LINE:
      fme_basicstring:22%17%22:{
        "query": "        @Value(_gql_rest)",
        "variables": {}
      }
    VAL_ATTR = _gql_rest
    -> HTTPCaller_5
HTTPCaller_5
    AUTH_METHOD_TYPE = NC
    AUTH_NAMED_CONNECTION = DAF GraphQL API Key v1
    CLIENT_CERTIFICATE_TYPE = NONE
    CONNECTION_TIMEOUT_LENGTH = 120
    CONTENT_TYPE_LOOKUP = application/json
    ERROR_ATTR = _error
    FOLLOW_REDIRECTS = FOLLOW_WITH_GET
    HTTP_METHOD = POST
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://graphql.datafordeler.dk/BBR/v1/
    TRANSFER_TIMEOUT_LENGTH = 180
    UPLOAD_BODY = @Value(_gql_rest)
    UPLOAD_TYPE = STRING_UPLOAD
    USE_COOKIES = No
    VERIFY_SSL_CERTIFICATES = Yes
    AUTH_METHOD = Web Connection
    UPLOAD_CONTENT_TYPE = JSON (application/json)

FME custom transformer GraphQLtoJSON

Parameters:
- GQL =   # GraphQL

Input (input)
    -> Junction_19
Output (output)

Bookmark: 2.GraphQL string to JSON payload (secret sauce) 🕵
Junction_19
    -> ParameterFetcher
Note: Create _gql_rest attribute
ParameterFetcher
    ATTR_LIST = _gql $(GQL) _gql_rest $(GQL)
    -> StringReplacer
Note: Replace LF with \n
StringReplacer
    CASE = NO
    FIND_TEXT = "\n"
    NO_MATCH = _FME_NO_OP_
    REGEXP = NO
    REPLACE_TEXT = \n
    SRC_ATTRS = _gql_rest
    -> StringReplacer_2
StringReplacer_2
    CASE = NO
    FIND_TEXT = "
    NO_MATCH = _FME_NO_OP_
    REGEXP = NO
    REPLACE_TEXT = \"
    SRC_ATTRS = _gql_rest
    -> StringConcatenator
StringConcatenator
    ACTION = Create New Attribute
    PARM_LINE:
      fme_basicstring:22%17%22:{
        "query": "        @Value(_gql_rest)",
        "variables": {}
      }
    VAL_ATTR = _gql_rest
    -> Junction_20
Note: Escape " with \"
Note: Wrap in Json query and variables
Junction_20
    -> Junction
Junction
    -> Output (output)
