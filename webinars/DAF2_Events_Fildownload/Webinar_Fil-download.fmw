FME workspace Webinar_Fil-download.fmw

Parameters:
- datasetName_raster = Overflade   # datasetName (raster)
- Register = GEODKV
- datasetName_filer = Soe   # datasetName (filer)
- MunicipalityCode = 0147
- FileFormat = gpkg   # File format
- MinX = 550109.24
- MaxX = 564444.62
- MinY = 6318802.38
- MaxY = 6326818.87
- datasetName_punktsky = Punktsky2015   # datasetName (punktsky)

Bookmark: Version 1
HTTPCaller_5
    AUTH_METHOD_TYPE = NC
    AUTH_NAMED_CONNECTION = DAF GraphQL API Key v1
    CLIENT_CERTIFICATE_TYPE = NONE
    CONNECTION_TIMEOUT_LENGTH = 60
    ERROR_ATTR = _error
    FOLLOW_REDIRECTS = FOLLOW_WITH_GET
    HTTP_METHOD = GET
    INPUT_PORT_CONNECTED = *
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://api.datafordeler.dk/FileDownloads/v1.0/GetAvailableFileDownloads
    TRANSFER_TIMEOUT_LENGTH = 90
    USE_COOKIES = No
    VERIFY_SSL_CERTIFICATES = Yes
    AUTH_METHOD = Web Connection
    -> JSONFragmenter_3
JSONFragmenter_3
    EXPLODE_FORMAT = JSON
    EXTRACT_ATTR = Yes
    INPUT_PORT_CONNECTED = CONNECTED
    JSON_ATTR = _response_body
    JSON_QUERY = json[*]
    NEW_ATTRIBUTES = municipalityCode buffer
    READ_FROM_FILE = NO
    RECURSIVE = YES
    REJECT_EMPTY_LISTS = YES

Bookmark: Hente alle objekter i BBR med version 2 (paging)
Note: BBR
HTTPCaller_3
    AUTH_METHOD_TYPE = NC
    AUTH_NAMED_CONNECTION = DAF GraphQL API Key v1
    CLIENT_CERTIFICATE_TYPE = NONE
    CONNECTION_TIMEOUT_LENGTH = 60
    ERROR_ATTR = _error
    FOLLOW_REDIRECTS = FOLLOW_WITH_GET
    HTTP_METHOD = GET
    INPUT_PORT_CONNECTED = *
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://api.datafordeler.dk/FileDownloads/v2.0/GetAvailableFileDownloads?Register=BBR
    TRANSFER_TIMEOUT_LENGTH = 90
    USE_COOKIES = No
    VERIFY_SSL_CERTIFICATES = Yes
    AUTH_METHOD = Web Connection
    -> JSONFragmenter_2
    -> JSONFragmenter
JSONFragmenter_2
    EXPLODE_FORMAT = JSON
    EXTRACT_ATTR = Yes
    INPUT_PORT_CONNECTED = CONNECTED
    JSON_ATTR = _response_body
    JSON_QUERY = json
    NEW_ATTRIBUTES = paginationMetadata.totalPages buffer
    READ_FROM_FILE = NO
    RECURSIVE = YES
    REJECT_EMPTY_LISTS = YES
    FRAGMENTS -> Cloner_4
Note: Opret det antal kloner, der svarer til antallet af sider i resultatet.
Cloner_4
    COPIES = @Value(paginationMetadata.totalPages)-1
    COPYATT = _copynum
    COPY -> HTTPCaller_4
HTTPCaller_4
    AUTH_METHOD_TYPE = NC
    AUTH_NAMED_CONNECTION = DAF GraphQL API Key v1
    CLIENT_CERTIFICATE_TYPE = NONE
    CONNECTION_TIMEOUT_LENGTH = 60
    ERROR_ATTR = _error
    FOLLOW_REDIRECTS = FOLLOW_WITH_GET
    HTTP_METHOD = GET
    INPUT_PORT_CONNECTED = CONNECTED
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://api.datafordeler.dk/FileDownloads/v2.0/GetAvailableFileDownloads?Register=BBR&PageNumber=@Value(_copynum)
    TRANSFER_TIMEOUT_LENGTH = 90
    USE_COOKIES = No
    VERIFY_SSL_CERTIFICATES = Yes
    AUTH_METHOD = Web Connection
    -> JSONFragmenter
JSONFragmenter
    EXPLODE_FORMAT = JSON
    EXTRACT_ATTR = Yes
    INPUT_PORT_CONNECTED = CONNECTED
    JSON_ATTR = _response_body
    JSON_QUERY = json["availableFileDownloads"][*]
    NEW_ATTRIBUTES = municipalityCode buffer fileName buffer typeOfData buffer typeOfDownload buffer entityName buffer containedFileFormat buffer fileSizeInBytes buffer frequency buffer expirationDate buffer
    READ_FROM_FILE = NO
    RECURSIVE = YES
    REJECT_EMPTY_LISTS = YES
    FRAGMENTS -> Tester_7
Tester_7
    BOOL_OP = OR
    TEST_CLAUSE = TEST @Value(municipalityCode) = 0147
    TEST_MODE = TEST
    PASSED -> Junction
Note: Alle filer i BBR inden for Frederiksbergs kommune
Junction

Bookmark: GetAvailableRasterFileDownloadsOverview
HTTPCaller_10
    AUTH_METHOD_TYPE = NC
    AUTH_NAMED_CONNECTION = DAF GraphQL API Key v1
    CLIENT_CERTIFICATE_TYPE = NONE
    CONNECTION_TIMEOUT_LENGTH = 60
    ERROR_ATTR = _error
    FOLLOW_REDIRECTS = FOLLOW_WITH_GET
    HTTP_METHOD = GET
    INPUT_PORT_CONNECTED = *
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://api.datafordeler.dk/FileDownloads/v1.0/GetAvailableRasterFileDownloadsOverview
    TRANSFER_TIMEOUT_LENGTH = 90
    USE_COOKIES = No
    VERIFY_SSL_CERTIFICATES = Yes
    AUTH_METHOD = Web Connection
    -> JSONFragmenter_7
JSONFragmenter_7
    EXPLODE_FORMAT = JSON
    EXTRACT_ATTR = Yes
    INPUT_PORT_CONNECTED = CONNECTED
    JSON_ATTR = _response_body
    JSON_QUERY = json[*]
    NEW_ATTRIBUTES = dataDeliveryNumber buffer dataSetName buffer fileFormat buffer recordCount buffer register buffer version buffer
    READ_FROM_FILE = NO
    RECURSIVE = YES
    REJECT_EMPTY_LISTS = YES
    FRAGMENTS -> Tester_2

Bookmark: Fildownload: Raster
Tester_2
    BOOL_OP = AND
    TEST_CLAUSE:
      TEST register ATTRIBUTE_HAS_A_VALUE ""
      TEST dataSetName ATTRIBUTE_HAS_A_VALUE ""
    TEST_MODE = TEST
    PASSED -> Tester_3
Note: Opret det antal kloner, der svarer til antallet af sider i resultatet.
Tester_3
    BOOL_OP = OR
    TEST_CLAUSE = TEST @Value(dataSetName) = $(datasetName_raster)
    TEST_MODE = TEST
    PASSED -> HTTPCaller_9
JSONFragmenter_4
    EXPLODE_FORMAT = JSON
    EXTRACT_ATTR = Yes
    INPUT_PORT_CONNECTED = CONNECTED
    JSON_ATTR = _response_body
    JSON_QUERY = json["availableFileDownloads"][*]
    NEW_ATTRIBUTES = fileName buffer id buffer
    READ_FROM_FILE = NO
    RECURSIVE = YES
    REJECT_EMPTY_LISTS = YES
    FRAGMENTS -> Sampler
    FRAGMENTS -> HTTPCaller_12
    FRAGMENTS -> HTTPCaller_11 [off]
Note: GetRasterMultipleSize
HTTPCaller_12
    AUTH_METHOD_TYPE = NC
    AUTH_NAMED_CONNECTION = DAF GraphQL API Key v1
    CLIENT_CERTIFICATE_TYPE = NONE
    CONNECTION_TIMEOUT_LENGTH = 60
    ERROR_ATTR = _error
    FOLLOW_REDIRECTS = FOLLOW_WITH_GET
    HTTP_METHOD = GET
    INPUT_PORT_CONNECTED = CONNECTED
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://api.datafordeler.dk/FileDownloads/GetRasterMultipleSize?register=@Value(register)&datasetname=@Value(dataSetName)&version=1&MinX=$(MinX)&MinY=$(MinY)&MaxX=$(MaxX)&MaxY=$(MaxY)
    TRANSFER_TIMEOUT_LENGTH = 90
    USE_COOKIES = No
    VERIFY_SSL_CERTIFICATES = Yes
    AUTH_METHOD = Web Connection
Sampler
    MODE = RANDOM
    RATE = 4
    SAMPLE_TYPE_MULTIPLIER = -1
    SAMPLE_MODE = Yes
    SAMPLE_TYPE_LONG = First N Features
    SAMPLED -> HTTPCaller_11
Note: GetRasterFile
HTTPCaller_11
    AUTH_METHOD_TYPE = NC
    AUTH_NAMED_CONNECTION = DAF GraphQL API Key v1
    CLIENT_CERTIFICATE_TYPE = NONE
    CONNECTION_TIMEOUT_LENGTH = 60
    ERROR_ATTR = _error
    FILE_PATH_ATTR = _response_file_path
    FOLLOW_REDIRECTS = FOLLOW_WITH_GET
    HTTP_METHOD = GET
    INPUT_PORT_CONNECTED = CONNECTED
    MAX_HTTP_VERSION = HTTP_2
    MAX_TRANSFERS_IN_PROGRESS = 25
    MINIMUM_ENCRYPTION_LEVEL = OS_DEFAULT
    OUTPUT_FILENAME = C:\Temp\DAF2_data\@Value(fileName)
    REDIRECT_AUTH = ORIGINAL_DOMAIN_ONLY
    RESPONSE_TYPE = File
    STATUS_CODE_ATTR = _http_status_code
    TARGET_URL = https://api.datafordeler.dk/FileDownloads/v1.0/GetRasterFile?FileName=@Value(fileName)
    TRANSFER_TIMEOUT_LENGTH = 3600
    USE_COOKIES = No
    VERIFY_SSL_CERTIFICATES = Yes
    AUTH_METHOD = Web Connection
    -> FeatureReader [INITIATOR]
FeatureReader
    ATTR_ACCUM_MODE = Only Use Result
    CLIP_TO_ENVELOPE = NO
    COMBINE_GEOM = Use Result
    DATASET = @Value(_response_file_path)
    FORMAT = GEOTIFF
    GEOTIFF_APPLY_GCPS = NO
    GEOTIFF_FEATURE_TYPE_NAME = FORMAT_NAME
    GEOTIFF_IGNORE_RASTER_TYPE_KEY = No
    GEOTIFF_LENIENT_READ = Yes
    GEOTIFF_NATIVELY_HANDLED_WEBSERVICES = s3connector,azurestorage,google-cloud-storage
    GEOTIFF_PREFER_FILE_CS_UNITS = Yes
    GEOTIFF_READER_META_ATTRIBUTES = fme_dataset fme_basename
    GEOTIFF_READ_OFFSETS_IN_CS_UNITS = No
    GEOTIFF_SCALE_COLOR_TO_STANDARD_BIT_DEPTH = YES
    GEOTIFF_USE_SEARCH_ENVELOPE = NO
    INITIATOR_FIRST_OUTPUT = default
    INPUT_PORT_INITIATOR_CONNECTED = CONNECTED
    INTERACT = NONE
    ORDER_RESULTS = No
    OUTPUT_ADD_SCHEMA_ATTRIBUTES = NO
    OUTPUT_FEATURES_DISPLAY = Schema and Data Features
    OUTPUT_USE_SCHEMA_CACHE = YES
    READER_BEHAVIOR = Constraint Parameters
    <OTHER> -> RasterMosaicker
RasterMosaicker
    ACCUM_ATTRS = ONE
    INTERPOLATION_TYPE = NearestNeighbor
    MERGE_PALETTES_NAME = Yes
    NODATA_OVERWRITE = No
    OVERLAPPING_VALUES = last
    SNAPPING_TYPE = RESAMPLE
    ACCUM_ATTRS_NAME = Use Attributes From One Feature
    INTERPOLATION_TYPE_NAME = Nearest Neighbor
    MERGE_PALETTES = Yes
    SNAPPING_TYPE_NAME = Resample

Bookmark: GetAvailableRasterFileDownloads: paging
HTTPCaller_9
    AUTH_METHOD_TYPE = NC
    AUTH_NAMED_CONNECTION = DAF GraphQL API Key v1
    CLIENT_CERTIFICATE_TYPE = NONE
    CONNECTION_TIMEOUT_LENGTH = 60
    ERROR_ATTR = _error
    FOLLOW_REDIRECTS = FOLLOW_WITH_GET
    HTTP_METHOD = GET
    INPUT_PORT_CONNECTED = CONNECTED
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://api.datafordeler.dk/FileDownloads/v1.0/GetAvailableRasterFileDownloads?Register=@Value(register)&FileFormat=tif&DataSetName=@Value(dataSetName)&MinX=$(MinX)&MinY=$(MinY)&MaxX=$(MaxX)&MaxY=$(MaxY)
    TRANSFER_TIMEOUT_LENGTH = 90
    USE_COOKIES = No
    VERIFY_SSL_CERTIFICATES = Yes
    AUTH_METHOD = Web Connection
    -> JSONFragmenter_4
    -> JSONFragmenter_10
JSONFragmenter_10
    EXPLODE_FORMAT = JSON
    EXTRACT_ATTR = Yes
    INPUT_PORT_CONNECTED = CONNECTED
    JSON_ATTR = _response_body
    JSON_QUERY = json["paginationMetadata"]
    NEW_ATTRIBUTES = totalPages buffer
    READ_FROM_FILE = NO
    RECURSIVE = YES
    REJECT_EMPTY_LISTS = YES
    FRAGMENTS -> Cloner_2
Cloner_2
    COPIES = @Value(totalPages)-1
    COPYATT = _copynum
    COPY -> AttributeCreator_15
AttributeCreator_15
    ATTR_TABLE = SET_TO _copynum (real64) = @Evaluate(@Value(_copynum)+2)
    INPUT_PORT_CONNECTED = CONNECTED
    -> HTTPCaller_18
HTTPCaller_18
    AUTH_METHOD_TYPE = NC
    AUTH_NAMED_CONNECTION = DAF GraphQL API Key v1
    CLIENT_CERTIFICATE_TYPE = NONE
    CONNECTION_TIMEOUT_LENGTH = 60
    ERROR_ATTR = _error
    FOLLOW_REDIRECTS = FOLLOW_WITH_GET
    HTTP_METHOD = GET
    INPUT_PORT_CONNECTED = CONNECTED
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://api.datafordeler.dk/FileDownloads/v1.0/GetAvailableRasterFileDownloads?Register=@Value(register)&FileFormat=tif&DataSetName=@Value(dataSetName)&MinX=$(MinX)&MinY=$(MinY)&MaxX=$(MaxX)&MaxY=$(MaxY)&PageNumber=@Value(_copynum)
    TRANSFER_TIMEOUT_LENGTH = 90
    USE_COOKIES = No
    VERIFY_SSL_CERTIFICATES = Yes
    AUTH_METHOD = Web Connection
    -> JSONFragmenter_4

Bookmark: GetAvailablePointCloudFileDownloadsOverview
HTTPCaller_14
    AUTH_METHOD_TYPE = NC
    AUTH_NAMED_CONNECTION = DAF GraphQL API Key v1
    CLIENT_CERTIFICATE_TYPE = NONE
    CONNECTION_TIMEOUT_LENGTH = 60
    ERROR_ATTR = _error
    FOLLOW_REDIRECTS = FOLLOW_WITH_GET
    HTTP_METHOD = GET
    INPUT_PORT_CONNECTED = *
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://api.datafordeler.dk/FileDownloads/v1.0/GetAvailablePointCloudFileDownloadsOverview
    TRANSFER_TIMEOUT_LENGTH = 90
    USE_COOKIES = No
    VERIFY_SSL_CERTIFICATES = Yes
    AUTH_METHOD = Web Connection
    -> JSONFragmenter_9
JSONFragmenter_9
    EXPLODE_FORMAT = JSON
    EXTRACT_ATTR = Yes
    INPUT_PORT_CONNECTED = CONNECTED
    JSON_ATTR = _response_body
    JSON_QUERY = json[*]
    NEW_ATTRIBUTES = dataDeliveryNumber buffer dataSetName buffer fileFormat buffer recordCount buffer register buffer version buffer
    READ_FROM_FILE = NO
    RECURSIVE = YES
    REJECT_EMPTY_LISTS = YES
    FRAGMENTS -> Tester_5

Bookmark: Fildownload: Punktsky
Tester_5
    BOOL_OP = AND
    TEST_CLAUSE:
      TEST register ATTRIBUTE_HAS_A_VALUE ""
      TEST dataSetName ATTRIBUTE_HAS_A_VALUE ""
    TEST_MODE = TEST
    PASSED -> Tester_6
Note: Opret det antal kloner, der svarer til antallet af sider i resultatet.
Tester_6
    BOOL_OP = OR
    TEST_CLAUSE = TEST @Value(dataSetName) = $(datasetName_punktsky)
    TEST_MODE = TEST
    PASSED -> HTTPCaller_13
    PASSED -> HTTPCaller_16
Note: GetPointCloudMultipleSize
HTTPCaller_16
    AUTH_METHOD_TYPE = NC
    AUTH_NAMED_CONNECTION = DAF GraphQL API Key v1
    CLIENT_CERTIFICATE_TYPE = NONE
    CONNECTION_TIMEOUT_LENGTH = 60
    ERROR_ATTR = _error
    FOLLOW_REDIRECTS = FOLLOW_WITH_GET
    HTTP_METHOD = GET
    INPUT_PORT_CONNECTED = CONNECTED
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://api.datafordeler.dk/FileDownloads/v1.0/GetPointCloudMultipleSize?Register=DHM&DataSetName=@Value(dataSetName)&MinX=$(MinX)&MinY=$(MinY)&MaxX=$(MaxX)&MaxY=$(MaxY)&Version=1
    TRANSFER_TIMEOUT_LENGTH = 90
    USE_COOKIES = No
    VERIFY_SSL_CERTIFICATES = Yes
    AUTH_METHOD = Web Connection
Sampler_2
    MODE = ORIGINAL
    RATE = 1
    SAMPLE_TYPE_MULTIPLIER = -1
    SAMPLE_MODE = No
    SAMPLE_TYPE_LONG = First N Features
    SAMPLED -> HTTPCaller_15
Note: GetPointCloudFile
HTTPCaller_15
    AUTH_METHOD_TYPE = NC
    AUTH_NAMED_CONNECTION = DAF GraphQL API Key v1
    CLIENT_CERTIFICATE_TYPE = NONE
    CONNECTION_TIMEOUT_LENGTH = 60
    ERROR_ATTR = _error
    FILE_PATH_ATTR = _response_file_path
    FOLLOW_REDIRECTS = FOLLOW_WITH_GET
    HTTP_METHOD = GET
    INPUT_PORT_CONNECTED = CONNECTED
    MAX_HTTP_VERSION = HTTP_2
    MAX_TRANSFERS_IN_PROGRESS = 25
    MINIMUM_ENCRYPTION_LEVEL = OS_DEFAULT
    OUTPUT_FILENAME = C:\Temp\DAF2_data\@Value(fileName)
    REDIRECT_AUTH = ORIGINAL_DOMAIN_ONLY
    RESPONSE_TYPE = File
    STATUS_CODE_ATTR = _http_status_code
    TARGET_URL = https://api.datafordeler.dk/FileDownloads/v1.0/GetPointCloudFile?FileName=@Value(fileName)
    TRANSFER_TIMEOUT_LENGTH = 90
    USE_COOKIES = No
    VERIFY_SSL_CERTIFICATES = Yes
    AUTH_METHOD = Web Connection
    -> FeatureReader_2 [INITIATOR]
FeatureReader_2
    ATTR_ACCUM_MODE = Only Use Result
    CLIP_TO_ENVELOPE = NO
    COMBINE_GEOM = Use Result
    DATASET = @Value(_response_file_path)
    FORMAT = LAS
    INITIATOR_FIRST_OUTPUT = default
    INPUT_PORT_INITIATOR_CONNECTED = CONNECTED
    INTERACT = NONE
    LAS_GROUP_BY_DATASET = No
    LAS_READER_META_ATTRIBUTES = fme_dataset
    LAS_RESOLUTION = 0
    LAS_USE_SEARCH_ENVELOPE = NO
    ORDER_RESULTS = No
    OUTPUT_ADD_SCHEMA_ATTRIBUTES = NO
    OUTPUT_FEATURES_DISPLAY = Schema and Data Features
    OUTPUT_USE_SCHEMA_CACHE = YES
    READER_BEHAVIOR = Constraint Parameters
    <OTHER> -> PointCloudSplitter
PointCloudSplitter
    OUTPUT_ATTR = _classification
    SPLIT_BY = classification
    SPLIT_TYPE = Unique
    SPLIT_BY_DISPLAY = classification
    SPLIT -> PointCloudLASClassifier [LAS_Point_Cloud]
PointCloudLASClassifier

Bookmark: GetAvailablePointCloudFileDownloads
HTTPCaller_13
    AUTH_METHOD_TYPE = NC
    AUTH_NAMED_CONNECTION = DAF GraphQL API Key v1
    CLIENT_CERTIFICATE_TYPE = NONE
    CONNECTION_TIMEOUT_LENGTH = 60
    ERROR_ATTR = _error
    FOLLOW_REDIRECTS = FOLLOW_WITH_GET
    HTTP_METHOD = GET
    INPUT_PORT_CONNECTED = CONNECTED
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://api.datafordeler.dk/FileDownloads/v1.0/GetAvailablePointCloudFileDownloads?Register=@Value(register)&DataSetName=@Value(dataSetName)&MinX=$(MinX)&MinY=$(MinY)&MaxX=$(MaxX)&MaxY=$(MaxY)
    TRANSFER_TIMEOUT_LENGTH = 90
    USE_COOKIES = No
    VERIFY_SSL_CERTIFICATES = Yes
    AUTH_METHOD = Web Connection
    -> JSONFragmenter_8
    -> JSONFragmenter_11
JSONFragmenter_11
    EXPLODE_FORMAT = JSON
    EXTRACT_ATTR = Yes
    INPUT_PORT_CONNECTED = CONNECTED
    JSON_ATTR = _response_body
    JSON_QUERY = json["paginationMetadata"]
    NEW_ATTRIBUTES = totalPages buffer
    READ_FROM_FILE = NO
    RECURSIVE = YES
    REJECT_EMPTY_LISTS = YES
    FRAGMENTS -> Cloner_3
Cloner_3
    COPIES = @Value(totalPages)-1
    COPYATT = _copynum
    COPY -> AttributeCreator_16
AttributeCreator_16
    ATTR_TABLE = SET_TO _copynum (real64) = @Evaluate(@Value(_copynum)+2)
    INPUT_PORT_CONNECTED = CONNECTED
    -> HTTPCaller_19
HTTPCaller_19
    AUTH_METHOD_TYPE = NC
    AUTH_NAMED_CONNECTION = DAF GraphQL API Key v1
    CLIENT_CERTIFICATE_TYPE = NONE
    CONNECTION_TIMEOUT_LENGTH = 60
    ERROR_ATTR = _error
    FOLLOW_REDIRECTS = FOLLOW_WITH_GET
    HTTP_METHOD = GET
    INPUT_PORT_CONNECTED = CONNECTED
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://api.datafordeler.dk/FileDownloads/v1.0/GetAvailablePointCloudFileDownloads?Register=@Value(register)&DataSetName=@Value(dataSetName)&MinX=$(MinX)&MinY=$(MinY)&MaxX=$(MaxX)&MaxY=$(MaxY)&PageNumber=@Value(_copynum)
    TRANSFER_TIMEOUT_LENGTH = 90
    USE_COOKIES = No
    VERIFY_SSL_CERTIFICATES = Yes
    AUTH_METHOD = Web Connection
    -> JSONFragmenter_8
JSONFragmenter_8
    EXPLODE_FORMAT = JSON
    EXTRACT_ATTR = Yes
    INPUT_PORT_CONNECTED = CONNECTED
    JSON_ATTR = _response_body
    JSON_QUERY = json["availableFileDownloads"][*]
    NEW_ATTRIBUTES = fileName buffer id buffer
    READ_FROM_FILE = NO
    RECURSIVE = YES
    REJECT_EMPTY_LISTS = YES
    FRAGMENTS -> Sampler_2

Bookmark: GetAvailableFileDownloads
HTTPCaller_20
    AUTH_METHOD_TYPE = NC
    AUTH_NAMED_CONNECTION = DAF GraphQL API Key v1
    CLIENT_CERTIFICATE_TYPE = NONE
    CONNECTION_TIMEOUT_LENGTH = 60
    ERROR_ATTR = _error
    FOLLOW_REDIRECTS = FOLLOW_WITH_GET
    HTTP_METHOD = GET
    INPUT_PORT_CONNECTED = *
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://api.datafordeler.dk/FileDownloads/v2.0/GetAvailableFileDownloads?Register=$(Register)&Entity=$(datasetName_filer)
    TRANSFER_TIMEOUT_LENGTH = 90
    USE_COOKIES = No
    VERIFY_SSL_CERTIFICATES = Yes
    AUTH_METHOD = Web Connection
    -> JSONFragmenter_5
JSONFragmenter_12
    EXPLODE_FORMAT = JSON
    EXTRACT_ATTR = Yes
    INPUT_PORT_CONNECTED = CONNECTED
    JSON_ATTR = _response_body
    JSON_QUERY = json["availableFileDownloads"][*]
    NEW_ATTRIBUTES = fileName buffer entityName buffer containedFileFormat buffer outputFileFormat buffer expirationDate buffer fileSizeInBytes buffer md5Hash buffer typeOfDownload buffer register buffer version buffer frequency buffer municipalityCode buffer
    READ_FROM_FILE = NO
    RECURSIVE = YES
    REJECT_EMPTY_LISTS = YES
    FRAGMENTS -> Tester

Bookmark: Fildownload
Note: Soe i GEODKV
JSONFragmenter_5
    EXPLODE_FORMAT = JSON
    EXTRACT_ATTR = Yes
    INPUT_PORT_CONNECTED = CONNECTED
    JSON_ATTR = _response_body
    JSON_QUERY = json
    NEW_ATTRIBUTES = paginationMetadata.totalPages buffer paginationMetadata.totalCount buffer
    READ_FROM_FILE = NO
    RECURSIVE = YES
    REJECT_EMPTY_LISTS = YES
    FRAGMENTS -> Tester_4
Tester_4
    BOOL_OP = OR
    TEST_CLAUSE = TEST @Value(paginationMetadata.totalPages) <= 1
    TEST_MODE = TEST
    PASSED -> JSONFragmenter_12
    FAILED -> Cloner_5
Note: Opret det antal kloner, der svarer til antallet af sider i resultatet.
Cloner_5
    COPIES = @Value(paginationMetadata.totalPages)-1
    COPYATT = _copynum
    COPY -> HTTPCaller_6
HTTPCaller_6
    AUTH_METHOD_TYPE = NC
    AUTH_NAMED_CONNECTION = DAF GraphQL API Key v1
    CLIENT_CERTIFICATE_TYPE = NONE
    CONNECTION_TIMEOUT_LENGTH = 60
    ERROR_ATTR = _error
    FOLLOW_REDIRECTS = FOLLOW_WITH_GET
    HTTP_METHOD = GET
    INPUT_PORT_CONNECTED = CONNECTED
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://api.datafordeler.dk/FileDownloads/v2.0/GetAvailableFileDownloads?Register=$(Register)&Entity=$(datasetName_filer)&PageNumber=@Value(_copynum)
    TRANSFER_TIMEOUT_LENGTH = 90
    USE_COOKIES = No
    VERIFY_SSL_CERTIFICATES = Yes
    AUTH_METHOD = Web Connection
    -> JSONFragmenter_12
Note: Filtrer efter: / Type download / Filformat / Aktuel (også tilgængelig: Temporal og Bitemporal) / Kommunekode
Tester
    BOOL_OP = AND
    TEST_CLAUSE:
      TEST @Value(typeOfDownload) = TotalDownload
      CASE_INSENSITIVE_TEST @Value(fileName) CONTAINS Current
      TEST @Value(containedFileFormat) = $(FileFormat)
      TEST @Value(municipalityCode) = $(MunicipalityCode)
    TEST_MODE = PER_TEST
    PASSED -> HTTPCaller_2
Note: GetFile
HTTPCaller_2
    AUTH_METHOD_TYPE = NC
    AUTH_NAMED_CONNECTION = DAF GraphQL API Key v1
    CLIENT_CERTIFICATE_TYPE = NONE
    CONNECTION_TIMEOUT_LENGTH = 60
    ERROR_ATTR = _error
    FILE_PATH_ATTR = _response_file_path
    FOLLOW_REDIRECTS = FOLLOW_WITH_GET
    HTTP_METHOD = GET
    INPUT_PORT_CONNECTED = CONNECTED
    MAX_HTTP_VERSION = HTTP_2
    MAX_TRANSFERS_IN_PROGRESS = 25
    MINIMUM_ENCRYPTION_LEVEL = OS_DEFAULT
    OUTPUT_FILENAME = C:\Temp\DAF2_data\@Value(fileName)
    REDIRECT_AUTH = ORIGINAL_DOMAIN_ONLY
    RESPONSE_TYPE = File
    STATUS_CODE_ATTR = _http_status_code
    TARGET_URL = https://api.datafordeler.dk/FileDownloads/v1.0/GetFile?Filename=@Value(fileName)
    TRANSFER_TIMEOUT_LENGTH = 3600
    USE_COOKIES = No
    VERIFY_SSL_CERTIFICATES = Yes
    AUTH_METHOD = Web Connection
    -> FeatureReader_4 [INITIATOR]
FeatureReader_4
    ATTR_ACCUM_MODE = Only Use Result
    CLIP_TO_ENVELOPE = NO
    COMBINE_GEOM = Use Result
    DATASET = @Value(_response_file_path)
    FORMAT = OGCGEOPACKAGE
    INITIATOR_FIRST_OUTPUT = default
    INPUT_PORT_INITIATOR_CONNECTED = CONNECTED
    INTERACT = NONE
    OGCGEOPACKAGE_ENCODE_FEATURE_TYPE_AND_ATTR_NAMES = YES
    OGCGEOPACKAGE_ENFORCE_FOREIGN_KEY_INTEGRITY = YES
    OGCGEOPACKAGE_EXPOSE_PRIMARY_KEY_ATTRIBUTE = YES
    OGCGEOPACKAGE_OPEN_SINGLE_RASTER_AS_SUBDATASET = YES
    OGCGEOPACKAGE_QUERY_FEATURE_TYPES_FOR_MERGE_FILTERS = Yes
    OGCGEOPACKAGE_READER_REPLACE_INVALID_CHARS = NO
    OGCGEOPACKAGE_READ_BOOLEANS_AS_YES_NO = YES
    OGCGEOPACKAGE_READ_NULLS = YES
    OGCGEOPACKAGE_USE_SEARCH_ENVELOPE = NO
    ORDER_RESULTS = No
    OUTPUT_ADD_SCHEMA_ATTRIBUTES = NO
    OUTPUT_FEATURES_DISPLAY = Schema and Data Features
    OUTPUT_USE_SCHEMA_CACHE = YES
    READER_BEHAVIOR = SELECTFEATTYPES
    <OTHER> -> Junction_2
Note: Soe inden for Frederiksbergs kommune
Junction_2

FME custom transformer PointCloudLASClassifier
The transformer uses _classification attribute for outputting each class through its own port. It also sets _classification_description attribute, which contains the explanation of the class assigned to a point cloud.
The transformer does not split the cloud, it only helps separate point clouds after splitting and easily identify the content of each class.
The classification values are assigned based on the standard ASPRS classification values:
0 - Created, never classified
1 - Unclassified
2 - Ground
3 - Low Vegetation
4 - Medium Vegetation
5 - High Vegetation
6 - Building
7 - Low Point (Noise)
8 - Model Key point (Mass Point)
9 - Water
10 - Reserved for ASPRS Definition
11 - Reserved fro ASPRS Definition
12 - Overlap Points
13-31 - Reserved for ASPRS Definition

Note: PointCloudLASClassifier is a custom transformer which routes point clouds into different output port depending on their classification attribute, which is assigned to point clouds / in PointCloudSplitter - this transformer should be placed before PointCloudLASClassifier. / PointCloudLASClassifier also adds a classification_description / attribute to each point cloud.
LAS_Point_Cloud (input)
    -> AttributeExposer
Note: Expose _classification attribute
AttributeExposer
    ATTR_LIST = _classification
    -> AttributeValueMapper
Note: Map the contents of the _classification attribute / to _classification_description attribute
AttributeValueMapper
    DEFAULT_VALUE = Reserved for ASPRS Definition
    LUT = 0,Created, never classified,1,Unclassified,2,Ground,3,Low Vegetation,4,Medium Vegetation,5,High Vegetation,6,Building,7,Low Point (noise),8,Model Key-point (mass point),9,Water,10,Reserved for ASPRS Definition,11,Reserved for ASPRS Definition,12,Overlap Points,13,Reserved for ASPRS Definition
    MAPPING_DIRECTION = FORWARD
    SRC = _classification
    VAL_ATTR = _classification_description
    DIRECTION = Forward (Source To Destination)
    -> PC
Note: Route point clouds into appriopriate ports / based on _classification attribute
PC: TestFilter
    DEFAULT_VALUE = <UNFILTERED>
    TEST_LIST = TEST_CLAUSE,"TEST @Value(_classification) = 0",TEST_LIST,"&_classification,=,0",TEST_MODE,Automatic,BOOL_OP,OR,0-Created(NeverClassified),TEST_CLAUSE,"TEST @Value(_classification) = 1",TEST_LIST,"&_classification,=,1",TEST_MODE,Automatic,BOOL_OP,OR,1-Unclassified,TEST_CLAUSE,"TEST @Value(_classification) = 2",TEST_LIST,"&_classification,=,2",TEST_MODE,Automatic,BOOL_OP,OR,2-Ground,TEST_CLAUSE,"TEST @Value(_classification) = 3",TEST_LIST,"&_classification,=,3",TEST_MODE,Automatic,BOOL_OP,OR,3-LowVegetation,TEST_CLAUSE,"TEST @Value(_classification) = 4",TEST_LIST,"&_classification,=,4",TEST_MODE,Automatic,BOOL_OP,OR,4-MediumVegetation,TEST_CLAUSE,"TEST @Value(_classification) = 5",TEST_LIST,"&_classification,=,5",TEST_MODE,Automatic,BOOL_OP,OR,5-HighVegetation,TEST_CLAUSE,"TEST @Value(_classification) = 6",TEST_LIST,"&_classification,=,6",TEST_MODE,Automatic,BOOL_OP,OR,6-Building,TEST_CLAUSE,"TEST @Value(_classification) = 7",TEST_LIST,"&_classification,=,7",TEST_MODE,Automatic,BOOL_OP,OR,7-LowPoint(Noise),TEST_CLAUSE,"TEST @Value(_classification) = 8",TEST_LIST,"&_classification,=,8",TEST_MODE,Automatic,BOOL_OP,OR,8-ModelKeyPoint(MassPoint),TEST_CLAUSE,"TEST @Value(_classification) = 9",TEST_LIST,"&_classification,=,9",TEST_MODE,Automatic,BOOL_OP,OR,9-Water,TEST_CLAUSE,"TEST @Value(_classification) = 10",TEST_LIST,"&_classification,=,10",TEST_MODE,Automatic,BOOL_OP,OR,10-Reserved for ASPRS Definition,TEST_CLAUSE,"TEST @Value(_classification) = 11",TEST_LIST,"&_classification,=,11",TEST_MODE,Automatic,BOOL_OP,OR,11-Reserved for ASPRS Definition,TEST_CLAUSE,"TEST @Value(_classification) = 12",TEST_LIST,"&_classification,=,12",TEST_MODE,Automatic,BOOL_OP,OR,12-OverlapPoints,TEST_CLAUSE,"TEST @Value(_classification) >= 13",TEST_LIST,"&_classification,>=,13",TEST_MODE,Automatic,BOOL_OP,OR,13more-Reserved for ASPRS Definition
    0-Created(NeverClassified) -> 0-Created/NeverClassified/ (output)
    1-Unclassified -> 1-Unclassified (output)
    2-Ground -> 2-Ground (output)
    3-LowVegetation -> 3-Low_Vegetation (output)
    4-MediumVegetation -> 4-Medium_Vegetation (output)
    5-HighVegetation -> 5-High_Vegetation (output)
    6-Building -> 6-Building (output)
    7-LowPoint(Noise) -> 7-Low_Point_/Noise/ (output)
    8-ModelKeyPoint(MassPoint) -> 8-Model_Key_Point_/Mass_Point/ (output)
    9-Water -> 9-Water (output)
    10-Reserved for ASPRS Definition -> 10_Reserved_for_ASPRS_Definition (output)
    11-Reserved for ASPRS Definition -> 11-Reserved_for_ASPRS_Definition (output)
    12-OverlapPoints -> 12-Overlap_Points (output)
    13more-Reserved for ASPRS Definition -> 13more-Reserved_for_ASPRS_Definition (output)
0-Created/NeverClassified/ (output)
1-Unclassified (output)
2-Ground (output)
3-Low_Vegetation (output)
4-Medium_Vegetation (output)
5-High_Vegetation (output)
6-Building (output)
7-Low_Point_/Noise/ (output)
8-Model_Key_Point_/Mass_Point/ (output)
9-Water (output)
10_Reserved_for_ASPRS_Definition (output)
11-Reserved_for_ASPRS_Definition (output)
12-Overlap_Points (output)
13more-Reserved_for_ASPRS_Definition (output)
