FME workspace DAF2_WFS-demo.fmw

Parameters:
- Kommune = 0147

SpatialFilter_2_Passed: Inspector
Note: Alle bygninger i bygning_current inden for det valgte kommuneomraade, uden duplikater
Junction_20

Bookmark: 1. GetCapabilities
Note: GetCapabilities BBR
HTTPCaller_5
    AUTH_METHOD_TYPE = NC
    AUTH_NAMED_CONNECTION = DAF GraphQL API Key v1
    CLIENT_CERTIFICATE_TYPE = NONE
    CONNECTION_TIMEOUT_LENGTH = 60
    ERROR_ATTR = _error
    FOLLOW_REDIRECTS = FOLLOW_WITH_GET
    HTTP_METHOD = GET
    INPUT_PORT_CONNECTED = *
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://wfs.datafordeler.dk/BBR/BBR_WFS/1.0.0/WFS?service=WFS&version=2.0.0&request=GetCapabilities
    TRANSFER_TIMEOUT_LENGTH = 90
    USE_COOKIES = No
    VERIFY_SSL_CERTIFICATES = Yes
    AUTH_METHOD = Web Connection
    -> XMLFragmenter_9
XMLFragmenter_9
    ATTRIBUTE_XML = _response_body
    DISABLE_EXTERNAL_ENTITY_PROCESSING = Yes
    EMBEDDED_EXPRESSIONS = FeatureType
    ENTITY_RESOLVER = Yes
    FEATURE_TYPES_FORMAT_NAME = XML
    FLATTEN_OPTIONS = <structure separator="." map-empty-elements="yes" matched-prefix="attributes" matched-attributes="yes" cardinality="+{?}" structure-prefix="" child-position-attribute="" except-expression="" ui-mode="basic" matched-ancestor-attributes="" exclude-xml-fragment-attribute="yes"/>
    IGNORE_DATASET_EXTERNAL_DTD = No
    INPUT_PORT_CONNECTED = CONNECTED
    MERGE_ATTRS = No
    NEW_ATTRIBUTES = Name buffer Title buffer Abstract buffer
    REJECT_FEATURES_WITH_NO_FRAGMENTS = YES
    XML_SOURCE_TYPE = xml_attr
    FRAGMENTS -> Junction_2
    <REJECTED> -> Junction_2
Note: GetCapabilities DAR
HTTPCaller_12
    AUTH_METHOD_TYPE = NC
    AUTH_NAMED_CONNECTION = DAF GraphQL API Key v1
    CLIENT_CERTIFICATE_TYPE = NONE
    CONNECTION_TIMEOUT_LENGTH = 60
    ERROR_ATTR = _error
    FOLLOW_REDIRECTS = FOLLOW_WITH_GET
    HTTP_METHOD = GET
    INPUT_PORT_CONNECTED = *
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://wfs.datafordeler.dk/DAR/DAR_WFS/1.0.0/WFS?service=WFS&version=2.0.0&request=GetCapabilities
    TRANSFER_TIMEOUT_LENGTH = 90
    USE_COOKIES = No
    VERIFY_SSL_CERTIFICATES = Yes
    AUTH_METHOD = Web Connection
    -> XMLFragmenter_7
XMLFragmenter_7
    ATTRIBUTE_XML = _response_body
    DISABLE_EXTERNAL_ENTITY_PROCESSING = Yes
    EMBEDDED_EXPRESSIONS = FeatureType
    ENTITY_RESOLVER = Yes
    FEATURE_TYPES_FORMAT_NAME = XML
    FLATTEN_OPTIONS = <structure separator="." map-empty-elements="yes" matched-prefix="attributes" matched-attributes="yes" cardinality="+{?}" structure-prefix="" child-position-attribute="" except-expression="" ui-mode="basic" matched-ancestor-attributes="" exclude-xml-fragment-attribute="yes"/>
    IGNORE_DATASET_EXTERNAL_DTD = No
    INPUT_PORT_CONNECTED = CONNECTED
    MERGE_ATTRS = No
    NEW_ATTRIBUTES = Name buffer Title buffer Abstract buffer
    REJECT_FEATURES_WITH_NO_FRAGMENTS = YES
    XML_SOURCE_TYPE = xml_attr
    FRAGMENTS -> Junction_2
    <REJECTED> -> Junction_2
Note: GetCapabilities GEODKV
HTTPCaller_4
    AUTH_METHOD_TYPE = NC
    AUTH_NAMED_CONNECTION = DAF GraphQL API Key v1
    CLIENT_CERTIFICATE_TYPE = NONE
    CONNECTION_TIMEOUT_LENGTH = 60
    ERROR_ATTR = _error
    FOLLOW_REDIRECTS = FOLLOW_WITH_GET
    HTTP_METHOD = GET
    INPUT_PORT_CONNECTED = *
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://wfs.datafordeler.dk/GEODKV/GEODKV_WFS/1.0.0/WFS?service=WFS&version=2.0.0&request=GetCapabilities
    TRANSFER_TIMEOUT_LENGTH = 90
    USE_COOKIES = No
    VERIFY_SSL_CERTIFICATES = Yes
    AUTH_METHOD = Web Connection
    -> XMLFragmenter_14
XMLFragmenter_14
    ATTRIBUTE_XML = _response_body
    DISABLE_EXTERNAL_ENTITY_PROCESSING = Yes
    EMBEDDED_EXPRESSIONS = FeatureType
    ENTITY_RESOLVER = Yes
    FEATURE_TYPES_FORMAT_NAME = XML
    FLATTEN_OPTIONS = <structure separator="." map-empty-elements="yes" matched-prefix="attributes" matched-attributes="yes" cardinality="+{?}" structure-prefix="" child-position-attribute="" except-expression="" ui-mode="basic" matched-ancestor-attributes="" exclude-xml-fragment-attribute="yes"/>
    IGNORE_DATASET_EXTERNAL_DTD = No
    INPUT_PORT_CONNECTED = CONNECTED
    MERGE_ATTRS = No
    NEW_ATTRIBUTES = Name buffer Title buffer Abstract buffer
    REJECT_FEATURES_WITH_NO_FRAGMENTS = YES
    XML_SOURCE_TYPE = xml_attr
    FRAGMENTS -> Junction_2
    <REJECTED> -> Junction_2
Note: GetCapabilities Fikspunkt
HTTPCaller
    AUTH_METHOD_TYPE = NC
    AUTH_NAMED_CONNECTION = DAF GraphQL API Key v1
    CLIENT_CERTIFICATE_TYPE = NONE
    CONNECTION_TIMEOUT_LENGTH = 60
    ERROR_ATTR = _error
    FOLLOW_REDIRECTS = FOLLOW_WITH_GET
    HTTP_METHOD = GET
    INPUT_PORT_CONNECTED = *
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://wfs.datafordeler.dk/FIKSPUNKT/FIKSPUNKT_WFS/1.0.0/WFS?service=WFS&version=2.0.0&request=GetCapabilities
    TRANSFER_TIMEOUT_LENGTH = 90
    USE_COOKIES = No
    VERIFY_SSL_CERTIFICATES = Yes
    AUTH_METHOD = Web Connection
    -> XMLFragmenter_11
XMLFragmenter_11
    ATTRIBUTE_XML = _response_body
    DISABLE_EXTERNAL_ENTITY_PROCESSING = Yes
    EMBEDDED_EXPRESSIONS = FeatureType
    ENTITY_RESOLVER = Yes
    FEATURE_TYPES_FORMAT_NAME = XML
    FLATTEN_OPTIONS = <structure separator="." map-empty-elements="yes" matched-prefix="attributes" matched-attributes="yes" cardinality="+{?}" structure-prefix="" child-position-attribute="" except-expression="" ui-mode="basic" matched-ancestor-attributes="" exclude-xml-fragment-attribute="yes"/>
    IGNORE_DATASET_EXTERNAL_DTD = No
    INPUT_PORT_CONNECTED = CONNECTED
    MERGE_ATTRS = No
    NEW_ATTRIBUTES = Name buffer Title buffer Abstract buffer
    REJECT_FEATURES_WITH_NO_FRAGMENTS = YES
    XML_SOURCE_TYPE = xml_attr
    FRAGMENTS -> Junction_2
    <REJECTED> -> Junction_2
Note: GetCapabilities DAGI
HTTPCaller_8
    AUTH_METHOD_TYPE = NC
    AUTH_NAMED_CONNECTION = DAF GraphQL API Key v1
    CLIENT_CERTIFICATE_TYPE = NONE
    CONNECTION_TIMEOUT_LENGTH = 60
    ERROR_ATTR = _error
    FOLLOW_REDIRECTS = FOLLOW_WITH_GET
    HTTP_METHOD = GET
    INPUT_PORT_CONNECTED = *
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://wfs.datafordeler.dk/DAGI/DAGI_WFS/1.0.0/WFS?service=WFS&version=2.0.0&request=GetCapabilities
    TRANSFER_TIMEOUT_LENGTH = 90
    USE_COOKIES = No
    VERIFY_SSL_CERTIFICATES = Yes
    AUTH_METHOD = Web Connection
    -> XMLFragmenter_15
XMLFragmenter_15
    ATTRIBUTE_XML = _response_body
    DISABLE_EXTERNAL_ENTITY_PROCESSING = Yes
    EMBEDDED_EXPRESSIONS = FeatureType
    ENTITY_RESOLVER = Yes
    FEATURE_TYPES_FORMAT_NAME = XML
    FLATTEN_OPTIONS = <structure separator="." map-empty-elements="yes" matched-prefix="attributes" matched-attributes="yes" cardinality="+{?}" structure-prefix="" child-position-attribute="" except-expression="" ui-mode="basic" matched-ancestor-attributes="" exclude-xml-fragment-attribute="yes"/>
    IGNORE_DATASET_EXTERNAL_DTD = No
    INPUT_PORT_CONNECTED = CONNECTED
    MERGE_ATTRS = No
    NEW_ATTRIBUTES = Name buffer Title buffer Abstract buffer
    REJECT_FEATURES_WITH_NO_FRAGMENTS = YES
    XML_SOURCE_TYPE = xml_attr
    FRAGMENTS -> Junction_2
    <REJECTED> -> Junction_2
Note: GetCapabilities DHMHoejdekurver
HTTPCaller_22
    AUTH_METHOD_TYPE = NC
    AUTH_NAMED_CONNECTION = DAF GraphQL API Key v1
    CLIENT_CERTIFICATE_TYPE = NONE
    CONNECTION_TIMEOUT_LENGTH = 60
    ERROR_ATTR = _error
    FOLLOW_REDIRECTS = FOLLOW_WITH_GET
    HTTP_METHOD = GET
    INPUT_PORT_CONNECTED = *
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://wfs.datafordeler.dk/DHMHoejdekurver/DHMHoejdekurver_WFS/1.0.0/WFS?service=WFS&version=2.0.0&request=GetCapabilities
    TRANSFER_TIMEOUT_LENGTH = 90
    USE_COOKIES = No
    VERIFY_SSL_CERTIFICATES = Yes
    AUTH_METHOD = Web Connection
    -> XMLFragmenter_18
XMLFragmenter_18
    ATTRIBUTE_XML = _response_body
    DISABLE_EXTERNAL_ENTITY_PROCESSING = Yes
    EMBEDDED_EXPRESSIONS = FeatureType
    ENTITY_RESOLVER = Yes
    FEATURE_TYPES_FORMAT_NAME = XML
    FLATTEN_OPTIONS = <structure separator="." map-empty-elements="yes" matched-prefix="attributes" matched-attributes="yes" cardinality="+{?}" structure-prefix="" child-position-attribute="" except-expression="" ui-mode="basic" matched-ancestor-attributes="" exclude-xml-fragment-attribute="yes"/>
    IGNORE_DATASET_EXTERNAL_DTD = No
    INPUT_PORT_CONNECTED = CONNECTED
    MERGE_ATTRS = No
    NEW_ATTRIBUTES = Name buffer Title buffer Abstract buffer
    REJECT_FEATURES_WITH_NO_FRAGMENTS = YES
    XML_SOURCE_TYPE = xml_attr
    FRAGMENTS -> Junction_2
    <REJECTED> -> Junction_2
Note: GetCapabilities DHMHoejdeOprindelse
HTTPCaller_20
    AUTH_METHOD_TYPE = NC
    AUTH_NAMED_CONNECTION = DAF GraphQL API Key v1
    CLIENT_CERTIFICATE_TYPE = NONE
    CONNECTION_TIMEOUT_LENGTH = 60
    ERROR_ATTR = _error
    FOLLOW_REDIRECTS = FOLLOW_WITH_GET
    HTTP_METHOD = GET
    INPUT_PORT_CONNECTED = *
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://wfs.datafordeler.dk/DHMOprindelse/DHMOprindelse_WFS/1.0.0/WFS?service=WFS&version=2.0.0&request=GetCapabilities
    TRANSFER_TIMEOUT_LENGTH = 90
    USE_COOKIES = No
    VERIFY_SSL_CERTIFICATES = Yes
    AUTH_METHOD = Web Connection
    -> XMLFragmenter_17
XMLFragmenter_17
    ATTRIBUTE_XML = _response_body
    DISABLE_EXTERNAL_ENTITY_PROCESSING = Yes
    EMBEDDED_EXPRESSIONS = FeatureType
    ENTITY_RESOLVER = Yes
    FEATURE_TYPES_FORMAT_NAME = XML
    FLATTEN_OPTIONS = <structure separator="." map-empty-elements="yes" matched-prefix="attributes" matched-attributes="yes" cardinality="+{?}" structure-prefix="" child-position-attribute="" except-expression="" ui-mode="basic" matched-ancestor-attributes="" exclude-xml-fragment-attribute="yes"/>
    IGNORE_DATASET_EXTERNAL_DTD = No
    INPUT_PORT_CONNECTED = CONNECTED
    MERGE_ATTRS = No
    NEW_ATTRIBUTES = Name buffer Title buffer Abstract buffer
    REJECT_FEATURES_WITH_NO_FRAGMENTS = YES
    XML_SOURCE_TYPE = xml_attr
    FRAGMENTS -> Junction_2
    <REJECTED> -> Junction_2
Note: GetCapabilities MAT
HTTPCaller_23
    AUTH_METHOD_TYPE = NC
    AUTH_NAMED_CONNECTION = DAF GraphQL API Key v1
    CLIENT_CERTIFICATE_TYPE = NONE
    CONNECTION_TIMEOUT_LENGTH = 60
    ERROR_ATTR = _error
    FOLLOW_REDIRECTS = FOLLOW_WITH_GET
    HTTP_METHOD = GET
    INPUT_PORT_CONNECTED = *
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://wfs.datafordeler.dk/MAT/MAT_WFS/1.0.0/WFS?service=WFS&version=2.0.0&request=GetCapabilities
    TRANSFER_TIMEOUT_LENGTH = 90
    USE_COOKIES = No
    VERIFY_SSL_CERTIFICATES = Yes
    AUTH_METHOD = Web Connection
    -> XMLFragmenter_19
XMLFragmenter_19
    ATTRIBUTE_XML = _response_body
    DISABLE_EXTERNAL_ENTITY_PROCESSING = Yes
    EMBEDDED_EXPRESSIONS = FeatureType
    ENTITY_RESOLVER = Yes
    FEATURE_TYPES_FORMAT_NAME = XML
    FLATTEN_OPTIONS = <structure separator="." map-empty-elements="yes" matched-prefix="attributes" matched-attributes="yes" cardinality="+{?}" structure-prefix="" child-position-attribute="" except-expression="" ui-mode="basic" matched-ancestor-attributes="" exclude-xml-fragment-attribute="yes"/>
    IGNORE_DATASET_EXTERNAL_DTD = No
    INPUT_PORT_CONNECTED = CONNECTED
    MERGE_ATTRS = No
    NEW_ATTRIBUTES = Name buffer Title buffer Abstract buffer
    REJECT_FEATURES_WITH_NO_FRAGMENTS = YES
    XML_SOURCE_TYPE = xml_attr
    FRAGMENTS -> Junction_2
    <REJECTED> -> Junction_2
Junction_2
    -> TestFilter
Note: Opdeling på current och hist tabeller
TestFilter
    DEFAULT_VALUE = <UNFILTERED>
    PASSED_TEST_GROUP_OUTPUT = FIRST
    TEST_LIST = "BOOL_OP,OR,COMPOSITE_TEST,""""""1"""""",TEST_CLAUSE,CASE_INSENSITIVE_TEST @Value(Title) CONTAINS _current",Current,"BOOL_OP,OR,COMPOSITE_TEST,""""""1"""""",TEST_CLAUSE,CASE_INSENSITIVE_TEST @Value(Title) CONTAINS _hist",Hist
    Current -> AttributeCreator_6
AttributeCreator_6
    ATTR_TABLE = SET_TO Register (varchar(200)) = @ReplaceRegularExpression(@Value(Name),_.*$,,caseSensitive=TRUE)
    INPUT_PORT_CONNECTED = CONNECTED
    -> Aggregator_2
Note: Enheder i _current per register
Aggregator_2
    ACCUM_ATTRS = None
    AGGREGATE_TYPE = Homogeneous Collection (If Possible)
    CONCAT_ATTRS = Title
    GROUP_BY = Register
    MODE = Geometry - Assemble One Level
    SEP = "\n"

Bookmark: 3.2 Hente Kommuneomraade (Frederiksberg) fra GEODKV
Note: GetFeature Kommuneomraade: exempel '0147', Frederiksbergs kommune
HTTPCaller_3
    AUTH_METHOD_TYPE = NC
    AUTH_NAMED_CONNECTION = DAF GraphQL API Key v1
    CLIENT_CERTIFICATE_TYPE = NONE
    CONNECTION_TIMEOUT_LENGTH = 60
    ERROR_ATTR = _error
    FOLLOW_REDIRECTS = FOLLOW_WITH_GET
    HTTP_METHOD = GET
    INPUT_PORT_CONNECTED = *
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://wfs.datafordeler.dk/GEODKV/GEODKV_WFS/1.0.0/WFS?request=GetFeature&TypeNames=kommuneomraade_current&cql_filter=kommunekode = '$(Kommune)'
    TRANSFER_TIMEOUT_LENGTH = 90
    USE_COOKIES = No
    VERIFY_SSL_CERTIFICATES = Yes
    AUTH_METHOD = Web Connection
    -> XMLFragmenter_5
XMLFragmenter_5
    ATTRIBUTE_XML = _response_body
    DISABLE_EXTERNAL_ENTITY_PROCESSING = Yes
    EMBEDDED_EXPRESSIONS = kommuneomraade_current
    ENTITY_RESOLVER = Yes
    FEATURE_TYPES_FORMAT_NAME = XML
    FLATTEN_OPTIONS = <structure separator="." map-empty-elements="yes" matched-prefix="attributes" matched-attributes="yes" cardinality="+{?}" structure-prefix="" child-position-attribute="" except-expression="" ui-mode="basic" matched-ancestor-attributes="" exclude-xml-fragment-attribute="yes"/>
    IGNORE_DATASET_EXTERNAL_DTD = No
    INPUT_PORT_CONNECTED = CONNECTED
    MERGE_ATTRS = No
    NEW_ATTRIBUTES = kommunekode buffer
    REJECT_FEATURES_WITH_NO_FRAGMENTS = YES
    XML_SOURCE_TYPE = xml_attr
    FRAGMENTS -> AttributeExposer
AttributeExposer
    ATTR_TABLE = geometri.Polygon.exterior.LinearRing.posList,,geometri.Polygon.interior.LinearRing.posList,,kommunekode,
    -> Counter
Counter
    CNT_ATTR = _count
    DOMAIN = counter
    SCOPE = Global
    START = 0
    -> AttributeSplitter_4
Note: For kommunale områder indeholder posList-attributten z-koordinater i en blanding af 0, -999 og korrekte værdier. Vi fjerner disse z-koordinater, før vi opretter polygoner.
AttributeSplitter_4
    ATTR_NAME = geometri.Polygon.exterior.LinearRing.posList
    DELIMITER = " "
    DROP_EMPTY_PARTS = NO
    LIST_NAME = _coords
    TRIM_TYPE = BOTH
    -> ListExploder_2
AttributeKeeper
    CREATE_BULK_MODE_FEATURES = NO
    -> LineCloser
LineCloser
    CONNECT_Z_MODE_LOOKUP = FIRST_WINS
    CONNECT_Z_MODE = First Wins
    AREA -> BoundingBoxReplacer
    AREA -> SpatialFilter [Filter]
    AREA -> Junction_13
    AREA -> Junction_17
Note: Clipper_3 : Clipper
Junction_13
    -> Junction_14
Note: Clipper_2 : Clipper
Junction_17
    -> Junction_18
Note: Kommuneomraader är for kompliceret til at sende til en query; skapa bounding box
BoundingBoxReplacer
    BBTYPE = BB
    BOXTYPE = 2D Bounding Box
    BOX -> BoundsExtractor
    BOX -> Junction_10
Note: GeometryExtractor_2 : Input
Junction_10
    -> Junction_12
BoundsExtractor
    XMAX = _xmax
    XMIN = _xmin
    YMAX = _ymax
    YMIN = _ymin
    ZMAX = _zmax
    ZMIN = _zmin
    -> AttributeCreator_7
AttributeCreator_7
    ATTR_TABLE:
      SET_TO TileX (real64) = @Evaluate(@floor((@Value(_xmax)-@Value(_xmin))/1500,0))
      SET_TO TileY (real64) = @Evaluate(@floor((@Value(_ymax)-@Value(_ymin))/1500,0))
    INPUT_PORT_CONNECTED = CONNECTED
    -> Tiler
Note: Skapa tiles, da hver query maksimalt kan returnere 10.000 objekter.
Tiler
    CLEANING_TOLERANCE_LOOKUP = AUTO
    COLUMN_ATTR = _column
    DUPLICATE_ON_TILE_BORDERS = NO
    INVALID_PART_HANDLING = REJECT_WHOLE_FEATURE
    MISSING_MEASURE_VALUES_LOOKUP = LINEAR_INTERPOLATION
    MISSING_Z_VALUES_LOOKUP = PLANAR_INTERPOLATION
    NUM_HORIZONTAL_TILES = @Value(TileX)
    NUM_VERTICAL_TILES = @Value(TileY)
    ROW_ATTR = _row
    STARTINGCORNER = BOTTOM_LEFT
    TILING_TYPE = NUM_TILES
    CLEANING_TOLERANCE = Automatic
    MISSING_MEASURE_VALUES = Linear Interpolation
    MISSING_Z_VALUES = Planar Interpolation
    TILED -> GeometryExtractor
Note: Ekstraher geometrien til WKT
GeometryExtractor
    ATTR = _geometryWKT
    KIND = wkt
    OGCVERSION = 1.2
    OGC_WKT_PRECISION = FLOAT_64
    REMOVE_GEOMETRY = No
    KIND_LONG = OGC Well Known Text
    OGC_WKT_PRECISION_DISPLAY = 64-bit
    -> AttributeKeeper_3
AttributeKeeper_3
    CREATE_BULK_MODE_FEATURES = NO
    KEEP_ATTRS = _geometryWKT
    -> HTTPCaller_10
    -> Junction_15
Note: HTTPCaller_13 : Input
Junction_15
    -> Junction_16

Bookmark: Correct coord list and create geometry
ListExploder_2
    ATTR_CONFLICT_RES_LOOKUP = INCOMING_IF_CONFLICT
    INDEX_ATTR = _element_index
    LIST_ATTR = _coords{}
    ATTR_ACCUM_MODE = Merge List Attributes
    ATTR_CONFLICT_RES = Use List Attribute Values
    ELEMENTS -> Tester
Tester
    BOOL_OP = OR
    TEST_CLAUSE = TEST @Value(_coords) < 300
    TEST_MODE = TEST
    FAILED -> ListBuilder
ListBuilder
    GROUP_BY = kommunekode
    LIST_ATTRS_TO_INCLUDE = _coords
    LIST_NAME = _list
    -> ListConcatenator
ListConcatenator
    DROP_EMPTY_PARTS = No
    LIST_ATTR = _list{}._coords
    SEP = " "
    VAL_ATTR = _concatenated
    -> StringReplacer_3
StringReplacer_3
    CASE = NO
    NO_MATCH = _FME_NO_OP_
    REGEXP = YES
    STR_REPLACE_TABLE = _concatenated (\S+\s+\S+)\s+ \1,
    -> AttributeCreator_2
AttributeCreator_2
    ATTR_TABLE = SET_TO wkt (varchar(200)) = LINESTRING (@Value(_concatenated))
    INPUT_PORT_CONNECTED = CONNECTED
    -> GeometryReplacer_2
GeometryReplacer_2
    KIND = wkt
    OGC_WKT_PRECISION = FLOAT_64
    REMOVE_ATTRIBUTE = No
    SOURCE = @Value(wkt)
    KIND_LONG = OGC Well Known Text
    OGC_WKT_PRECISION_DISPLAY = 64-bit
    -> CoordinateSystemSetter_4
CoordinateSystemSetter_4
    COORDSYS = EPSG:25832
    -> AttributeKeeper

Bookmark: 4. Sammanlign med GraphQL for GEODKV Bygning
Note: LineCloser : Area
Junction_14
    -> SpatialFilter_2 [Filter]
Note: BoundingBoxReplacer : Box
Junction_12
    -> GeometryExtractor_2
Note: Ekstraher geometrien til WKT
GeometryExtractor_2
    ATTR = _geometryWKT
    KIND = wkt
    OGCVERSION = 1.2
    OGC_WKT_PRECISION = FLOAT_64
    REMOVE_GEOMETRY = No
    KIND_LONG = OGC Well Known Text
    OGC_WKT_PRECISION_DISPLAY = 64-bit
    -> AttributeCreator_3
Note: Assign default for bbox if not given, and default VirkningFra and RegistreringFra to current datetime.
AttributeCreator_3
    ATTR_TABLE:
      SET_TO query.VirkningFra (varchar(200)) = FME_CONDITIONAL:DEFAULT_VALUE'_FME_NO_OP_'BOOL_OP;OR;COMPOSITE_TEST;1;TEST query.VirkningFra NOT_ATTRIBUTE_HAS_A_VALUE _FME_BLANK_STRING_'@DateTimeFormat(@DateTimeNow(),%Y-%m-%dT%H:%M:%SZ)'FME_NUM_CONDITIONS2___
      SET_TO query.RegistreringFra (varchar(200)) = FME_CONDITIONAL:DEFAULT_VALUE'_FME_NO_OP_'BOOL_OP;OR;COMPOSITE_TEST;1;TEST query.RegistreringFra NOT_ATTRIBUTE_HAS_A_VALUE _FME_BLANK_STRING_'@DateTimeFormat(@DateTimeNow(),%Y-%m-%dT%H:%M:%SZ)'FME_NUM_CONDITIONS2___
    -> AttributeCreator_4
Note: Create query
AttributeCreator_4
    ATTR_TABLE:
      SET_TO _gql (varchar(200)) = query {
            GEODKV_Bygning(
                virkningstid: "@Value(query.VirkningFra)",
                registreringstid: "@Value(query.RegistreringFra)"
                first: 1000
                where: {
                    geometri: {
                        intersects: {
                            crs: 25832
                            wkt: "@Value(_geometryWKT)"
                        }
                    }
                }
            ) {
            pageInfo {
              endCursor
              hasNextPage
            }
            nodes
                {
                applikation
                BBRaktion
                BBRUUID
                bygningstype
                dataansvar
                datafordelerOpdateringstid
                datafordelerRegisterImportSequenceNumber
                datafordelerRowId
                datafordelerRowVersion
                feltliste
                forretningshaendelse
                forretningsomraade
                forretningsproces
                geometri {
                    crs
                    wkt
                }
                geometristatus
                id_lokalId
                id_namespace
                kommentar
                maalestedBygning
                metode3D
                objectid
                overlapBygning
                planNoejagtighed
                planStedfaestelsesmetode
                registreringFra
                registreringsaktoer
                registreringsspecifikation
                registreringTil
                status
                synligBygning
                tempID
                underMinimumBygning
                vertikalNoejagtighed
                vertikalStedfaestelsesmetode
                virkningFra
                virkningsaktoer
                virkningTil
                }
            }
        }
    -> StringReplacer_5
StringReplacer_5
    CASE = NO
    FIND_TEXT = virkningstid: "",<pipe>registreringstid: ""
    NO_MATCH = _FME_NO_OP_
    REGEXP = YES
    SRC_ATTRS = _gql
    -> AttributeCopier_3
AttributeCopier_3
    ATTR_TABLE = COPY _gql > _gql_rest
    MISSING_INPUT_ATTRS = REMOVE
    -> StringReplacer_2
StringReplacer_2
    CASE = NO
    FIND_TEXT = "\n"
    NO_MATCH = _FME_NO_OP_
    REGEXP = NO
    REPLACE_TEXT = \n
    SRC_ATTRS = _gql_rest
    -> StringReplacer_4
StringReplacer_4
    CASE = NO
    FIND_TEXT = "
    NO_MATCH = _FME_NO_OP_
    REGEXP = NO
    REPLACE_TEXT = \"
    SRC_ATTRS = _gql_rest
    -> StringConcatenator_2
StringConcatenator_2
    ACTION = Create New Attribute
    PARM_LINE:
      fme_basicstring:22%17%22:{
        "query": "        @Value(_gql_rest)",
        "variables": {}
      }
    VAL_ATTR = _gql_rest
    -> HTTPCaller_16
Note: Get GEODKV_Bygning from "flexible"
HTTPCaller_16
    AUTH_METHOD_TYPE = NC
    AUTH_NAMED_CONNECTION = DAF GraphQL API Key v1
    CLIENT_CERTIFICATE_TYPE = NONE
    CONNECTION_TIMEOUT_LENGTH = 60
    CONTENT_TYPE_LOOKUP = application/json
    ERROR_ATTR = _error
    FOLLOW_REDIRECTS = FOLLOW_WITH_GET
    HTTP_METHOD = POST
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://graphql.datafordeler.dk/flexible/v1/
    TRANSFER_TIMEOUT_LENGTH = 90
    UPLOAD_BODY = @Value(_gql_rest)
    UPLOAD_TYPE = STRING_UPLOAD
    USE_COOKIES = No
    VERIFY_SSL_CERTIFICATES = Yes
    AUTH_METHOD = Web Connection
    UPLOAD_CONTENT_TYPE = JSON (application/json)
    -> JSONFragmenter_3
JSONFragmenter_3
    EXPLODE_FORMAT = JSON
    EXTRACT_ATTR = Yes
    JSON_ATTR = _response_body
    JSON_QUERY = json[*][*]
    NEW_ATTRIBUTES = nodes{} buffer pageInfo.endCursor buffer pageInfo.hasNextPage buffer
    READ_FROM_FILE = NO
    RECURSIVE = YES
    REJECT_EMPTY_LISTS = YES
    FRAGMENTS -> Tester_3
    <REJECTED> -> Junction_3
Note: Is there a next page?
Tester_3
    BOOL_OP = OR
    TEST_CLAUSE = TEST @Value(pageInfo.hasNextPage) = Yes
    TEST_MODE = TEST
    PASSED -> Junction_9
    PASSED -> VariableSetter
    FAILED -> Junction_9
Junction_9
    -> Junction_8
Note: Global variable vEndCursor / has the next cursor
VariableSetter
    SCOPE = Global
    VALUE = @Value(pageInfo.endCursor)
    VARNAME = vEndCursor
    -> Cloner
Note: Max 40 calls. / Possibly 40000 records
Cloner
    COPIES = 40
    COPYATT = _copynum
    COPY -> VariableRetriever
Note: Look ahead for new cursor in global variable
VariableRetriever
    SCOPE = Global
    VALUE_ATTR = _v_cursor
    VARNAME = vEndCursor
    -> Tester_9
    <REJECTED> -> Junction_3
Note: Last page?
Tester_9
    BOOL_OP = OR
    TEST_CLAUSE = TEST @Value(_v_cursor) != lastpage
    TEST_MODE = TEST
    PASSED -> StringReplacer
Note: Replace to enter paging info to sub-sequent queries
StringReplacer
    CASE = NO
    NO_MATCH = _FME_NO_OP_
    REGEXP = YES
    STR_REPLACE_TABLE = _gql (\s*)(first: \d*) \1\2\1after: "@Value(_v_cursor)"
    -> GraphQLtoJSON_2
GraphQLtoJSON_2
    GQL = @Value(_gql)
    -> AttributeRemover_3
AttributeRemover_3
    LIST_ATTRS = nodes{}
    -> HTTPCaller_17
HTTPCaller_17
    AUTH_METHOD_TYPE = NC
    AUTH_NAMED_CONNECTION = DAF GraphQL API Key v1
    CLIENT_CERTIFICATE_TYPE = NONE
    CONNECTION_TIMEOUT_LENGTH = 60
    CONTENT_TYPE_LOOKUP = application/json
    ERROR_ATTR = _error
    FOLLOW_REDIRECTS = FOLLOW_WITH_GET
    HTTP_METHOD = POST
    MAX_HTTP_VERSION = HTTP_2
    MAX_TRANSFERS_IN_PROGRESS = 1
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://graphql.datafordeler.dk/flexible/v1/
    TRANSFER_TIMEOUT_LENGTH = 90
    UPLOAD_BODY = @Value(_gql_rest)
    UPLOAD_TYPE = STRING_UPLOAD
    USE_COOKIES = No
    VERIFY_SSL_CERTIFICATES = Yes
    AUTH_METHOD = Web Connection
    UPLOAD_CONTENT_TYPE = JSON (application/json)
    -> JSONFragmenter_2
    <REJECTED> -> Junction_4
JSONFragmenter_2
    EXPLODE_FORMAT = JSON
    EXTRACT_ATTR = Yes
    JSON_ATTR = _response_body
    JSON_QUERY = json[*][*]
    NEW_ATTRIBUTES = nodes{} buffer pageInfo.endCursor buffer pageInfo.hasNextPage buffer
    READ_FROM_FILE = NO
    RECURSIVE = YES
    REJECT_EMPTY_LISTS = YES
    FRAGMENTS -> Tester_8
    <REJECTED> -> Junction_6
Tester_8
    BOOL_OP = OR
    TEST_CLAUSE = TEST @Value(pageInfo.hasNextPage) = Yes
    TEST_MODE = TEST
    PASSED -> VariableSetter_2
    FAILED -> VariableSetter_3
VariableSetter_2
    SCOPE = Global
    VALUE = @Value(pageInfo.endCursor)
    VARNAME = vEndCursor
    -> Junction_11
VariableSetter_3
    SCOPE = Global
    VALUE = lastpage
    VARNAME = vEndCursor
    -> Junction_11
Junction_11
    -> Junction_8
Junction_8
    -> JSONFragmenter
JSONFragmenter
    EXPLODE_FORMAT = JSON
    EXTRACT_ATTR = Yes
    INPUT_PORT_CONNECTED = CONNECTED
    JSON_ATTR = _response_body
    JSON_QUERY = json["nodes"][*]
    READ_FROM_FILE = NO
    RECURSIVE = YES
    REJECT_EMPTY_LISTS = YES
    FRAGMENTS -> AttributeExposer_5
AttributeExposer_5
    ATTR_TABLE = applikation,,BBRaktion,,BBRUUID,,bygningstype,,dataansvar,,datafordelerOpdateringstid,,datafordelerRegisterImportSequenceNumber,,datafordelerRowId,,datafordelerRowVersion,,feltliste,,forretningshaendelse,,forretningsomraade,,forretningsproces,,geometri.crs,,geometri.wkt,,geometristatus,,id_lokalId,,id_namespace,,kommentar,,maalestedBygning,,metode3D,,objectid,,overlapBygning,,planNoejagtighed,,planStedfaestelsesmetode,,registreringFra,,registreringsaktoer,,registreringsspecifikation,,registreringTil,,status,,synligBygning,,tempID,,underMinimumBygning,,vertikalNoejagtighed,,vertikalStedfaestelsesmetode,,virkningFra,,virkningsaktoer,,virkningTil,
    -> AttributeKeeper_2
AttributeKeeper_2
    CREATE_BULK_MODE_FEATURES = NO
    KEEP_ATTRS = id_lokalId,status,registreringFra,virkningFra,id_namespace,datafordelerOpdateringstid,forretningshaendelse,forretningsomraade,forretningsproces,BBRUUID,BBRaktion,applikation,bygningstype,dataansvar,datafordelerRegisterImportSequenceNumber,datafordelerRowId,datafordelerRowVersion,feltliste,geometri.crs,geometri.wkt,geometristatus,kommentar,maalestedBygning,metode3D,objectid,overlapBygning,planNoejagtighed,planStedfaestelsesmetode,registreringTil,registreringsaktoer,registreringsspecifikation,synligBygning,tempID,underMinimumBygning,vertikalNoejagtighed,vertikalStedfaestelsesmetode,virkningTil,virkningsaktoer
    -> AttributeCreator_18
AttributeCreator_18
    ATTR_TABLE = SET_TO _coordsys (varchar(200)) = EPSG:@Value(geometri.crs)
    -> CoordinateSystemSetter_6
CoordinateSystemSetter_6
    COORDSYS = @Value(_coordsys)
    -> GeometryReplacer_4
GeometryReplacer_4
    KIND = wkt
    OGC_WKT_PRECISION = FLOAT_64
    REMOVE_ATTRIBUTE = Yes
    SOURCE = @Value(geometri.wkt)
    KIND_LONG = OGC Well Known Text
    OGC_WKT_PRECISION_DISPLAY = 64-bit
    -> SpatialFilter_2 [Candidate]
SpatialFilter_2
    AGGREGATE_HANDLING = Yes
    BASE_TYPE = Multiple Filters
    CURVE_BOUNDARY_RULE_PARAM = Default Rule
    PASS_CRITERIA = Pass Against One Filter
    PREDATTR = _predicate
    PREDICATES = INTERSECTS
    USE_BOUNDING_BOX = No
    PASSED -> SpatialFilter_2_Passed
Note: To: error logging
Junction_6
    -> Junction_7
Note: JSONFragmenter_2 : rejected
Junction_7
    -> Junction_3
Note: AttributeCreator_11 : to error logging
Junction_4
    -> Junction_3
Junction_3
DAF2_SchemaInfo
    DAF_Flexible_URL = https://graphql.datafordeler.dk/flexible/v1/schema
    GetSchemaDataset = GEODKV
    GetSchemaForEntity = Bygning
    apikey =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

Bookmark: 5. GetFeature - sammenligne json og gml, hente navngivenvej_current
Note: LineCloser : Area
Junction_18
    -> Clipper_2 [CLIPPER]
Note: GeometryExtractor : Output
Junction_16
    -> HTTPCaller_13
Note: GetFeature DAR navngivenvej_current
HTTPCaller_13
    AUTH_METHOD_TYPE = NC
    AUTH_NAMED_CONNECTION = DAF GraphQL API Key v1
    CLIENT_CERTIFICATE_TYPE = NONE
    CONNECTION_TIMEOUT_LENGTH = 60
    ERROR_ATTR = _error
    FOLLOW_REDIRECTS = FOLLOW_WITH_GET
    HTTP_METHOD = GET
    INPUT_PORT_CONNECTED = CONNECTED
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://wfs.datafordeler.dk/DAR/DAR_WFS/1.0.0/WFS?service=WFS&version=2.0.0&request=GetFeature&typeName=navngivenvej_current&cql_filter=INTERSECTS(vejnavnebeliggenhed_vejnavnelinje,@Value(_geometryWKT))
    TRANSFER_TIMEOUT_LENGTH = 90
    USE_COOKIES = No
    VERIFY_SSL_CERTIFICATES = Yes
    AUTH_METHOD = Web Connection
    -> XMLFragmenter_8
XMLFragmenter_8
    ATTRIBUTE_XML = _response_body
    DISABLE_EXTERNAL_ENTITY_PROCESSING = Yes
    EMBEDDED_EXPRESSIONS = navngivenvej_current
    ENTITY_RESOLVER = Yes
    FEATURE_TYPES_FORMAT_NAME = XML
    FLATTEN_OPTIONS = <structure separator="." map-empty-elements="yes" matched-prefix="attributes" matched-attributes="yes" cardinality="+{?}" structure-prefix="" child-position-attribute="" except-expression="" ui-mode="basic" matched-ancestor-attributes="" exclude-xml-fragment-attribute="yes"/>
    IGNORE_DATASET_EXTERNAL_DTD = No
    INPUT_PORT_CONNECTED = CONNECTED
    MERGE_ATTRS = No
    NEW_ATTRIBUTES = Name buffer Title buffer Abstract buffer
    REJECT_FEATURES_WITH_NO_FRAGMENTS = YES
    XML_SOURCE_TYPE = xml_attr
    FRAGMENTS -> Counter_2
Counter_2
    CNT_ATTR = _count
    DOMAIN = counter
    SCOPE = Global
    START = 0
    -> AttributeExposer_3
AttributeExposer_3
    ATTR_TABLE = vejnavnebeliggenhed_vejnavnelinje.MultiCurve.curveMember{}.LineString.posList,,vejnavn,,administreresAfKommune,,id_lokalId,,id_namespace,,navngivenvej_current.id,,status,,udtaltVejnavn,
    -> ListExploder_3
ListExploder_3
    ATTR_CONFLICT_RES_LOOKUP = INCOMING_IF_CONFLICT
    INDEX_ATTR = _element_index
    LIST_ATTR = vejnavnebeliggenhed_vejnavnelinje.MultiCurve.curveMember{}
    ATTR_ACCUM_MODE = Merge List Attributes
    ATTR_CONFLICT_RES = Use List Attribute Values
    ELEMENTS -> AttributeCreator
    <REJECTED> -> AttributeExposer_4
AttributeExposer_4
    ATTR_TABLE = vejnavnebeliggenhed_vejnavnelinje.MultiCurve.curveMember.LineString.posList,
    -> AttributeCreator
AttributeCreator
    ATTR_TABLE:
      SET_TO GMLGeom (varchar(200)) = FME_CONDITIONAL:DEFAULT_VALUE'_FME_NO_OP_'BOOL_OP;OR;COMPOSITE_TEST;1;TEST LineString.posList ATTRIBUTE_HAS_A_VALUE _FME_BLANK_STRING_'<gml:LineString>
          <gml:posList>@Value(LineString.posList)</gml:posList>
        </gml:LineString>'BOOL_OP;OR;COMPOSITE_TEST;1;TEST vejnavnebeliggenhed_vejnavnelinje.MultiCurve.curveMember.LineString.posList ATTRIBUTE_HAS_A_VALUE _FME_BLANK_STRING_'<gml:LineString>
          <gml:posList>@Value(vejnavnebeliggenhed_vejnavnelinje.MultiCurve.curveMember.LineString.posList)</gml:posList>
        </gml:LineString>'FME_NUM_CONDITIONS3___
    INPUT_PORT_CONNECTED = CONNECTED
    -> GeometryReplacer
GeometryReplacer
    KIND = GML
    REMOVE_ATTRIBUTE = Yes
    SOURCE = @Value(GMLGeom)
    SRS_AXIS_ORDER_DISPLAY = Automatic
    KIND_LONG = GML
    -> CoordinateSystemSetter_3
CoordinateSystemSetter_3
    COORDSYS = EPSG:25832
    -> Aggregator
Aggregator
    ACCUM_ATTRS = One
    AGGREGATE_TYPE = Homogeneous Collection (If Possible)
    GROUP_BY = _count
    LIST_ATTRS_TO_INCLUDE = id_lokalId udtaltVejnavn
    LIST_NAME = _objects
    MODE = Geometry - Assemble One Level
    SEP = ,
    AGGREGATE -> Clipper_2 [CANDIDATE]
Clipper_2
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> Junction
Note: Alle navngivenvej_current inden for det valgte kommuneomraade
Junction
Note: GetFeature BBR bygning_current som json
HTTPCaller_15
    AUTH_METHOD_TYPE = NC
    AUTH_NAMED_CONNECTION = DAF GraphQL API Key v1
    CLIENT_CERTIFICATE_TYPE = NONE
    CONNECTION_TIMEOUT_LENGTH = 120
    ERROR_ATTR = _error
    FILE_PATH_ATTR = _response_file_path
    FOLLOW_REDIRECTS = FOLLOW_WITH_GET
    HTTP_METHOD = GET
    INPUT_PORT_CONNECTED = *
    MAX_HTTP_VERSION = HTTP_2
    MAX_TRANSFERS_IN_PROGRESS = 25
    MINIMUM_ENCRYPTION_LEVEL = OS_DEFAULT
    OUTPUT_FILENAME = $(FME_MF_DIR_USERTYPED)\BBR_WFS_download.json
    REDIRECT_AUTH = ORIGINAL_DOMAIN_ONLY
    RESPONSE_TYPE = File
    STATUS_CODE_ATTR = _http_status_code
    TARGET_URL = https://wfs.datafordeler.dk/BBR/BBR_WFS/1.0.0/WFS?service=WFS&version=2.0.0&request=GetFeature&TypeNames=bygning_current&outputFormat=json
    TRANSFER_TIMEOUT_LENGTH = 90
    USE_COOKIES = No
    VERIFY_SSL_CERTIFICATES = Yes
    AUTH_METHOD = Web Connection
    -> FeatureReader_2 [INITIATOR]
FeatureReader_2
    ATTRIBUTES = bygning_current,"type,id,geometry.type,geometry.coordinates{},geometry_name,properties.forretningshændelse,properties.forretningsområde,properties.forretningsproces,properties.id_namespace,properties.id_lokalId,properties.kommunekode,properties.registreringFra,properties.registreringsaktør,properties.registreringTil,properties.virkningFra,properties.virkningsaktør,properties.virkningTil,properties.status,properties.byg007Bygningsnummer,properties.byg021BygningensAnvendelse,properties.byg024AntalLejlighederMedKøkken,properties.byg025AntalLejlighederUdenKøkken,properties.byg026Opførelsesår,properties.byg027OmTilbygningsår,properties.byg029DatoForMidlertidigOpførtBygning,properties.byg030Vandforsyning,properties.byg031Afløbsforhold,properties.byg032YdervæggensMateriale,properties.byg033Tagdækningsmateriale,properties.byg034SupplerendeYdervæggensMateriale,properties.byg035SupplerendeTagdækningsMateriale,properties.byg036AsbestholdigtMateriale,properties.byg037KildeTilBygningensMaterialer,properties.byg038SamletBygningsareal,properties.byg039BygningensSamledeBoligAreal,properties.byg040BygningensSamledeErhvervsAreal,properties.byg041BebyggetAreal,properties.byg042ArealIndbyggetGarage,properties.byg043ArealIndbyggetCarport,properties.byg044ArealIndbyggetUdhus,properties.byg045ArealIndbyggetUdestueEllerLign,properties.byg046SamletArealAfLukkedeOverdækningerPåBygningen,properties.byg047ArealAfAffaldsrumITerrænniveau,properties.byg048AndetAreal,properties.byg049ArealAfOverdækketAreal,properties.byg050ArealÅbneOverdækningerPåBygningenSamlet,properties.byg051Adgangsareal,properties.byg052BeregningsprincipCarportAreal,properties.byg053BygningsarealerKilde,properties.byg054AntalEtager,properties.byg055AfvigendeEtager,properties.byg056Varmeinstallation,properties.byg057Opvarmningsmiddel,properties.byg058SupplerendeVarme,properties.byg069Sikringsrumpladser,properties.byg070Fredning,properties.byg071BevaringsværdighedReference,properties.byg094Revisionsdato,properties.byg111StormrådetsOversvømmelsesSelvrisiko,properties.byg112DatoForRegistreringFraStormrådet,properties.byg113Byggeskadeforsikringsselskab,properties.byg114DatoForByggeskadeforsikring,properties.byg119Udledningstilladelse,properties.byg121OmfattetAfByggeskadeforsikring,properties.byg122Gyldighedsdato,properties.byg123MedlemskabAfSpildevandsforsyning,properties.byg124PåbudVedrSpildevandsafledning,properties.byg125FristVedrSpildevandsafledning,properties.byg126TilladelseTilUdtræden,properties.byg127DatoForTilladelseTilUdtræden,properties.byg128TilladelseTilAlternativBortskaffelseEllerAfledning,properties.byg129DatoForTilladelseTilAlternativBortskaffelseEllerAfledning,properties.byg130ArealAfUdvendigEfterisolering,properties.byg131DispensationFritagelseIftKollektivVarmeforsyning,properties.byg132DatoForDispensationFritagelseIftKollektivVarmeforsyning,properties.byg133KildeTilKoordinatsæt,properties.byg134KvalitetAfKoordinatsæt,properties.byg135SupplerendeOplysningOmKoordinatsæt,properties.byg136PlaceringPåSøterritorie,properties.byg137BanedanmarkBygværksnummer,properties.byg301TypeAfFlytning,properties.byg302Tilflytterkommune,properties.byg403ØvrigeBemærkningerFraStormrådet,properties.byg406Koordinatsystem,properties.byg500Notatlinjer,properties.byg150Gulvbelægning,properties.byg151Frihøjde,properties.byg152ÅbenLukketKonstruktion,properties.byg153Konstruktionsforhold,properties.byg140ServitutForUdlejningsEjendomDato,properties.jordstykke,properties.husnummer,properties.ejerlejlighed,properties.grund,json_fragment,geometry"
    ATTR_ACCUM_MODE = Only Use Result
    COMBINE_GEOM = Use Result
    DATASET = C:\Users\SEHHAN\OneDrive - Sweco AB\FME\DAF2\WFS\BBR_WFS_download.json
    FEATURETYPES = bygning_current
    FORMAT = JSON
    INITIATOR_FIRST_OUTPUT = default
    INPUT_PORT_INITIATOR_CONNECTED = CONNECTED
    JSON_COORDINATE_SYSTEM_KEY = 25832
    JSON_FEATURE_TYPE_KEY = bygning_current
    JSON_FLATTEN_MODE = ALL_LEVELS
    JSON_GEOMETRY_FORMAT = GeoJSON
    JSON_GEOMETRY_KEY = geometri
    JSON_QUERY_TABLE = bygning_current json["features"][*]
    JSON_SAVE_FRAGMENTS = YES
    JSON_SCAN_MODE = QUERY
    JSON_USE_SEARCH_ENVELOPE = NO
    ORDER_RESULTS = No
    OUTPUT_ADD_SCHEMA_ATTRIBUTES = NO
    OUTPUT_FEATURES_DISPLAY = Schema and Data Features
    OUTPUT_USE_SCHEMA_CACHE = YES
    READER_BEHAVIOR = Constraint Parameters
    bygning_current -> VertexCreator_3
VertexCreator_3
    COORDSYS = EPSG:25832
    MEASURE_TYPE_LOOKUP = CONTINUOUS
    MODE = REPLACE
    REMOVE_ATTRIBUTES = No
    XVAL = @Value(geometry.coordinates{0})
    YVAL = @Value(geometry.coordinates{1})
    MEASURE_TYPE = Continuous
    MODE_NAME = Replace with Point
    <REJECTED> -> VertexCreator_3__Rejected_
VertexCreator_3__Rejected_: Logger
    LOG_FEATURE = LOG_ONLY
    MAXCOORDS = 20
    MAXFEATS = 20
    MESSAGE = Feature is:
    SEVERITY = INFO
Note: GetFeature BBR bygning_current som gml
HTTPCaller_7
    AUTH_METHOD_TYPE = NC
    AUTH_NAMED_CONNECTION = DAF GraphQL API Key v1
    CLIENT_CERTIFICATE_TYPE = NONE
    CONNECTION_TIMEOUT_LENGTH = 120
    ERROR_ATTR = _error
    FILE_PATH_ATTR = _response_file_path
    FOLLOW_REDIRECTS = FOLLOW_WITH_GET
    HTTP_METHOD = GET
    INPUT_PORT_CONNECTED = *
    MAX_HTTP_VERSION = HTTP_2
    MAX_TRANSFERS_IN_PROGRESS = 25
    MINIMUM_ENCRYPTION_LEVEL = OS_DEFAULT
    OUTPUT_FILENAME = $(FME_MF_DIR_USERTYPED)\BBR_WFS_download.gml
    REDIRECT_AUTH = ORIGINAL_DOMAIN_ONLY
    RESPONSE_TYPE = File
    STATUS_CODE_ATTR = _http_status_code
    TARGET_URL = https://wfs.datafordeler.dk/BBR/BBR_WFS/1.0.0/WFS?service=WFS&version=2.0.0&request=GetFeature&TypeNames=bygning_current&outputFormat=gml32
    TRANSFER_TIMEOUT_LENGTH = 90
    USE_COOKIES = No
    VERIFY_SSL_CERTIFICATES = Yes
    AUTH_METHOD = Web Connection
    -> FeatureReader [INITIATOR]
FeatureReader
    ATTRIBUTES = bygning_current,"byg007Bygningsnummer,byg021BygningensAnvendelse,byg026Opførelsesår,byg027OmTilbygningsår,byg029DatoForMidlertidigOpførtBygning,byg030Vandforsyning,byg031Afløbsforhold,byg032YdervæggensMateriale,byg033Tagdækningsmateriale,byg034SupplerendeYdervæggensMateriale,byg035SupplerendeTagdækningsMateriale,byg036AsbestholdigtMateriale,byg037KildeTilBygningensMaterialer,byg038SamletBygningsareal,byg039BygningensSamledeBoligAreal,byg040BygningensSamledeErhvervsAreal,byg041BebyggetAreal,byg042ArealIndbyggetGarage,byg043ArealIndbyggetCarport,byg044ArealIndbyggetUdhus,byg045ArealIndbyggetUdestueEllerLign,byg046SamletArealAfLukkedeOverdækningerPåBygningen,byg047ArealAfAffaldsrumITerrænniveau,byg048AndetAreal,byg049ArealAfOverdækketAreal,byg051Adgangsareal,byg053BygningsarealerKilde,byg054AntalEtager,byg055AfvigendeEtager,byg056Varmeinstallation,byg057Opvarmningsmiddel,byg058SupplerendeVarme,byg069Sikringsrumpladser,byg070Fredning,byg094Revisionsdato,byg111StormrådetsOversvømmelsesSelvrisiko,byg112DatoForRegistreringFraStormrådet,byg113Byggeskadeforsikringsselskab,byg114DatoForByggeskadeforsikring,byg119Udledningstilladelse,byg121OmfattetAfByggeskadeforsikring,byg122Gyldighedsdato,byg124PåbudVedrSpildevandsafledning,byg125FristVedrSpildevandsafledning,byg130ArealAfUdvendigEfterisolering,byg133KildeTilKoordinatsæt,byg134KvalitetAfKoordinatsæt,byg135SupplerendeOplysningOmKoordinatsæt,byg136PlaceringPåSøterritorie,byg140ServitutForUdlejningsEjendomDato,byg403ØvrigeBemærkningerFraStormrådet,byg404Koordinat.Point.id,byg404Koordinat.Point.pos,byg404Koordinat.Point.srsDimension,byg404Koordinat.Point.srsName,byg406Koordinatsystem,bygning_current.id,forretningshændelse,forretningsområde,forretningsproces,grund,husnummer,id_lokalId,id_namespace,jordstykke,kommunekode,registreringFra,registreringsaktør,status,virkningFra,virkningsaktør,xml_fragment,xml_id,xml_matched_element,xml_parent_child_pos,xml_parent_id"
    ATTR_ACCUM_MODE = Only Use Result
    CLIP_TO_ENVELOPE = NO
    COMBINE_GEOM = Use Result
    DATASET = C:\Users\SEHHAN\OneDrive - Sweco AB\FME\DAF2\WFS\BBR_WFS_download.gml
    FEATURETYPES = bygning_current
    FORMAT = XML
    INITIATOR_FIRST_OUTPUT = default
    INPUT_PORT_INITIATOR_CONNECTED = CONNECTED
    INTERACT = NONE
    ORDER_RESULTS = No
    OUTPUT_ADD_SCHEMA_ATTRIBUTES = NO
    OUTPUT_FEATURES_DISPLAY = Schema and Data Features
    OUTPUT_USE_SCHEMA_CACHE = YES
    READER_BEHAVIOR = Constraint Parameters
    XML_CONTINUE_ON_GEOM_ERROR = no
    XML_CREATE_ENTITY_RESOLVER = Yes
    XML_DISABLE_EXTERNAL_ENTITY_PROCESSING = yes
    XML_FILE_TYPE = Feature Paths
    XML_IGNORE_DATASET_EXTERNAL_DTD = no
    XML_SUPPORTED_READER_ARCHIVE_EXTENSIONS = xml.gz,gml.gz
    XML_USE_SEARCH_ENVELOPE = NO
    XML_VALIDATE_DATASET = no
    XML_VALIDATE_XFMAP = no
    XML_XFMAP_FEATURE_PATHS = FeatureCollection/member/bygning_current
    XML_XFMAP_FEATURE_PATHS_STRUCTURE:
      <structure
      separator="."
      map-empty-elements="yes"
      matched-prefix="attributes"
      matched-attributes="yes"
      cardinality="+{?}"
      except-expression=""
      structure-prefix=""
      child-position-attribute=""
      attribute-identifier=""
      ui-mode="basic"/>
    bygning_current -> AttributeSplitter
AttributeSplitter
    ATTR_NAME = byg404Koordinat.Point.pos
    DELIMITER = " "
    DROP_EMPTY_PARTS = NO
    LIST_NAME = _coordinateList
    TRIM_TYPE = BOTH
    -> VertexCreator
VertexCreator
    COORDSYS = EPSG:25832
    MEASURE_TYPE_LOOKUP = CONTINUOUS
    MODE = REPLACE
    REMOVE_ATTRIBUTES = No
    XVAL = @Value(_coordinateList{0})
    YVAL = @Value(_coordinateList{1})
    MEASURE_TYPE = Continuous
    MODE_NAME = Replace with Point
    <REJECTED> -> Logger
Logger
    LOG_FEATURE = LOG_ONLY
    MAXCOORDS = 20
    MAXFEATS = 20
    MESSAGE = Feature is:
    SEVERITY = INFO

Bookmark: 3.3 Hent data fra GEODKV WFS inden for det valgte kommuneomraade
Note: GetFeature GEODKV bygning_current
Note: Søg med BoundingBox
HTTPCaller_10
    AUTH_METHOD_TYPE = NC
    AUTH_NAMED_CONNECTION = DAF GraphQL API Key v1
    CLIENT_CERTIFICATE_TYPE = NONE
    CONNECTION_TIMEOUT_LENGTH = 120
    ERROR_ATTR = _error
    FOLLOW_REDIRECTS = FOLLOW_WITH_GET
    HTTP_METHOD = GET
    INPUT_PORT_CONNECTED = CONNECTED
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://wfs.datafordeler.dk/GEODKV/GEODKV_WFS/1.0.0/WFS?request=GetFeature&TypeNames=bygning_current&cql_filter=INTERSECTS(geometri,@Value(_geometryWKT))
    TRANSFER_TIMEOUT_LENGTH = 90
    USE_COOKIES = No
    VERIFY_SSL_CERTIFICATES = Yes
    AUTH_METHOD = Web Connection
    -> XMLFragmenter_13
XMLFragmenter_13
    ATTRIBUTE_XML = _response_body
    DISABLE_EXTERNAL_ENTITY_PROCESSING = Yes
    EMBEDDED_EXPRESSIONS = bygning_current
    ENTITY_RESOLVER = Yes
    FEATURE_TYPES_FORMAT_NAME = XML
    FLATTEN_OPTIONS = <structure separator="." map-empty-elements="yes" matched-prefix="attributes" matched-attributes="yes" cardinality="+{?}" structure-prefix="" child-position-attribute="" except-expression="" ui-mode="basic" matched-ancestor-attributes="" exclude-xml-fragment-attribute="yes"/>
    IGNORE_DATASET_EXTERNAL_DTD = No
    INPUT_PORT_CONNECTED = CONNECTED
    MERGE_ATTRS = No
    NEW_ATTRIBUTES = geometri.Polygon.exterior.LinearRing.posList buffer geometri.Polygon.interior.LinearRing.posList buffer id.lokalId buffer geometri.Polygon.srsDimension buffer
    REJECT_FEATURES_WITH_NO_FRAGMENTS = YES
    XML_SOURCE_TYPE = xml_attr
    FRAGMENTS -> AttributeCreator_5
Note: Opret GML-geometri, og brug attributterne srsDimension og posList til at oprette: / <gml:Polygon> / <gml:exterior> / <gml:LinearRing xmlns:gml="http://www.opengis.net/gml" srsName="EPSG:25832" srsDimension="@Value(geometri.Polygon.srsDimension)"> / <gml:posList> / @Value(geometri.Polygon.exterior.LinearRing.posList) / </gml:posList> / </gml:LinearRing> / </gml:exterior> / <gml:interior> / <gml:LinearRing xmlns:gml="http://www.opengis.net/gml" srsName="EPSG:25832" srsDimension="@Value(geometri.Polygon.srsDimension)"> / <gml:posList> / @Value(geometri.Polygon.interior.LinearRing.posList) / </gml:posList> / </gml:LinearRing> / </gml:interior> / </gml:Polygon>
AttributeCreator_5
    ATTR_TABLE:
      SET_TO GMLGeom (varchar(200)) = FME_CONDITIONAL:DEFAULT_VALUE'_FME_NO_OP_'BOOL_OP;OR;COMPOSITE_TEST;1;TEST geometri.Polygon.interior.LinearRing.posList NOT_ATTRIBUTE_HAS_A_VALUE _FME_BLANK_STRING_'<gml:Polygon>
            <gml:exterior>
                <gml:LinearRing xmlns:gml="http://www.opengis.net/gml" srsName="EPSG:25832" srsDimension="@Value(geometri.Polygon.srsDimension)">
                    <gml:posList>
                        @Value(geometri.Polygon.exterior.LinearRing.posList)
                    </gml:posList>
                </gml:LinearRing>
            </gml:exterior>
        </gml:Polygon>'BOOL_OP;OR;COMPOSITE_TEST;1;TEST geometri.Polygon.interior.LinearRing.posList ATTRIBUTE_HAS_A_VALUE _FME_BLANK_STRING_'<gml:Polygon>
            <gml:exterior>
                <gml:LinearRing xmlns:gml="http://www.opengis.net/gml" srsName="EPSG:25832" srsDimension="@Value(geometri.Polygon.srsDimension)">
                    <gml:posList>
                        @Value(geometri.Polygon.exterior.LinearRing.posList)
                    </gml:posList>
                </gml:LinearRing>
            </gml:exterior>
                <gml:interior>
                <gml:LinearRing xmlns:gml="http://www.opengis.net/gml" srsName="EPSG:25832" srsDimension="@Value(geometri.Polygon.srsDimension)">
                    <gml:posList>
                        @Value(geometri.Polygon.interior.LinearRing.posList)
                    </gml:posList>
                </gml:LinearRing>
            </gml:interior>
        </gml:Polygon>'FME_NUM_CONDITIONS3___
    INPUT_PORT_CONNECTED = CONNECTED
    -> GeometryReplacer_3
GeometryReplacer_3
    KIND = GML
    REMOVE_ATTRIBUTE = Yes
    SOURCE = @Value(GMLGeom)
    SRS_AXIS_ORDER_DISPLAY = Automatic
    KIND_LONG = GML
    -> CoordinateSystemSetter_5
CoordinateSystemSetter_5
    COORDSYS = EPSG:25832
    -> AttributeRemover
AttributeRemover
    REMOVE_ATTRS = xml_fragment,xml_id,xml_matched_element,xml_parent_child_pos,xml_parent_id,id.lokalId
    -> SpatialFilter [Candidate]
Note: Filtre med den faktiske polygon
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> Junction_5
Note: Alle bygninger i bygning_current i GEODKV inden for det valgte kommuneomraade, inkluderer overlappende match fra forskellige tiles
Junction_5
    -> AttributeExposer_2
AttributeExposer_2
    ATTR_TABLE = bygning_current.id,,geometri.Polygon.id,,id_lokalId,,objectid,
    -> DuplicateFilter
DuplicateFilter
    INPUT_ORDERED_CHOICE_LOOKUP = NO
    KEYATTR = objectid
    INPUT_ORDERED_CHOICE = No
    UNIQUE -> Junction_20

Bookmark: 2. DescribeFeatureType
Note: DescribeFeatureType GEODKV bygning_current
HTTPCaller_19
    AUTH_METHOD_TYPE = NC
    AUTH_NAMED_CONNECTION = DAF GraphQL API Key v1
    CLIENT_CERTIFICATE_TYPE = NONE
    CONNECTION_TIMEOUT_LENGTH = 60
    ERROR_ATTR = _error
    FOLLOW_REDIRECTS = FOLLOW_WITH_GET
    HTTP_METHOD = GET
    INPUT_PORT_CONNECTED = *
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://wfs.datafordeler.dk/GEODKV/GEODKV_WFS/1.0.0/WFS?service=WFS&version=2.0.0&request=DescribeFeatureType&typeName=bygning_current
    TRANSFER_TIMEOUT_LENGTH = 90
    USE_COOKIES = No
    VERIFY_SSL_CERTIFICATES = Yes
    AUTH_METHOD = Web Connection
    -> XMLFragmenter_2
XMLFragmenter_2
    ATTRIBUTE_XML = _response_body
    DISABLE_EXTERNAL_ENTITY_PROCESSING = Yes
    EMBEDDED_EXPRESSIONS = schema
    ENTITY_RESOLVER = Yes
    FEATURE_TYPES_FORMAT_NAME = XML
    FLATTEN_OPTIONS = <structure separator="." map-empty-elements="yes" matched-prefix="attributes" matched-attributes="yes" cardinality="+{?}" structure-prefix="" child-position-attribute="" except-expression="" ui-mode="basic" matched-ancestor-attributes="" exclude-xml-fragment-attribute="yes"/>
    IGNORE_DATASET_EXTERNAL_DTD = No
    INPUT_PORT_CONNECTED = CONNECTED
    MERGE_ATTRS = No
    NEW_ATTRIBUTES = complexType.complexContent.extension.sequence.element{}.name buffer complexType.complexContent.extension.sequence.element{}.type buffer complexType.complexContent.extension.sequence.element{}.nillable buffer complexType.complexContent.extension.sequence.element{}.maxOccurs buffer complexType.complexContent.extension.sequence.element{}.minOccurs buffer
    REJECT_FEATURES_WITH_NO_FRAGMENTS = YES
    XML_SOURCE_TYPE = xml_attr
    FRAGMENTS -> ListExploder_5
ListExploder_5
    ATTR_CONFLICT_RES_LOOKUP = INCOMING_IF_CONFLICT
    INDEX_ATTR = _element_index
    LIST_ATTR = complexType.complexContent.extension.sequence.element{}
    ATTR_ACCUM_MODE = Merge List Attributes
    ATTR_CONFLICT_RES = Use List Attribute Values
    ELEMENTS -> AttributeFilter_2
Note: Datatyper i GEODKV bygning_current
AttributeFilter_2
    ATTR_NAME = type
    ATTR_VALUES = <Empty>,<Missing>,<Null>,<Unfiltered>,gml:SurfacePropertyType,xsd:boolean,xsd:dateTime,xsd:string

Bookmark: Andra register
Note: DescribeFeatureType BBR bygning_current
HTTPCaller_24
    AUTH_METHOD_TYPE = NC
    AUTH_NAMED_CONNECTION = DAF GraphQL API Key v1
    CLIENT_CERTIFICATE_TYPE = NONE
    CONNECTION_TIMEOUT_LENGTH = 60
    ERROR_ATTR = _error
    FOLLOW_REDIRECTS = FOLLOW_WITH_GET
    HTTP_METHOD = GET
    INPUT_PORT_CONNECTED = *
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://wfs.datafordeler.dk/BBR/BBR_WFS/1.0.0/WFS?service=WFS&version=2.0.0&request=DescribeFeatureType&typeName=bygning_current
    TRANSFER_TIMEOUT_LENGTH = 90
    USE_COOKIES = No
    VERIFY_SSL_CERTIFICATES = Yes
    AUTH_METHOD = Web Connection
    -> XMLFragmenter_20
XMLFragmenter_20
    ATTRIBUTE_XML = _response_body
    DISABLE_EXTERNAL_ENTITY_PROCESSING = Yes
    EMBEDDED_EXPRESSIONS = schema
    ENTITY_RESOLVER = Yes
    FEATURE_TYPES_FORMAT_NAME = XML
    FLATTEN_OPTIONS = <structure separator="." map-empty-elements="yes" matched-prefix="attributes" matched-attributes="yes" cardinality="+{?}" structure-prefix="" child-position-attribute="" except-expression="" ui-mode="basic" matched-ancestor-attributes="" exclude-xml-fragment-attribute="yes"/>
    IGNORE_DATASET_EXTERNAL_DTD = No
    INPUT_PORT_CONNECTED = CONNECTED
    MERGE_ATTRS = No
    NEW_ATTRIBUTES = complexType.complexContent.extension.sequence.element{}.name buffer complexType.complexContent.extension.sequence.element{}.type buffer complexType.complexContent.extension.sequence.element{}.nillable buffer complexType.complexContent.extension.sequence.element{}.maxOccurs buffer complexType.complexContent.extension.sequence.element{}.minOccurs buffer
    REJECT_FEATURES_WITH_NO_FRAGMENTS = YES
    XML_SOURCE_TYPE = xml_attr
    FRAGMENTS -> ListExploder_7
ListExploder_7
    ATTR_CONFLICT_RES_LOOKUP = INCOMING_IF_CONFLICT
    INDEX_ATTR = _element_index
    LIST_ATTR = complexType.complexContent.extension.sequence.element{}
    ATTR_ACCUM_MODE = Merge List Attributes
    ATTR_CONFLICT_RES = Use List Attribute Values
    ELEMENTS -> AttributeFilter
Note: Datatyper i BBR bygning_current
AttributeFilter
    ATTR_NAME = type
    ATTR_VALUES = <Empty>,<Missing>,<Null>,<Unfiltered>,gml:PointPropertyType,xsd:dateTime,xsd:double,xsd:long,xsd:string
Note: DescribeFeatureType MAT jordstykketemaflade_currend
HTTPCaller_21
    AUTH_METHOD_TYPE = NC
    AUTH_NAMED_CONNECTION = DAF GraphQL API Key v1
    CLIENT_CERTIFICATE_TYPE = NONE
    CONNECTION_TIMEOUT_LENGTH = 60
    ERROR_ATTR = _error
    FOLLOW_REDIRECTS = FOLLOW_WITH_GET
    HTTP_METHOD = GET
    INPUT_PORT_CONNECTED = *
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://wfs.datafordeler.dk/MAT/MAT_WFS/1.0.0/WFS?service=WFS&version=2.0.0&request=DescribeFeatureType&typeName=jordstykketemaflade_current
    TRANSFER_TIMEOUT_LENGTH = 90
    USE_COOKIES = No
    VERIFY_SSL_CERTIFICATES = Yes
    AUTH_METHOD = Web Connection
    -> XMLFragmenter_16
XMLFragmenter_16
    ATTRIBUTE_XML = _response_body
    DISABLE_EXTERNAL_ENTITY_PROCESSING = Yes
    EMBEDDED_EXPRESSIONS = schema
    ENTITY_RESOLVER = Yes
    FEATURE_TYPES_FORMAT_NAME = XML
    FLATTEN_OPTIONS = <structure separator="." map-empty-elements="yes" matched-prefix="attributes" matched-attributes="yes" cardinality="+{?}" structure-prefix="" child-position-attribute="" except-expression="" ui-mode="basic" matched-ancestor-attributes="" exclude-xml-fragment-attribute="yes"/>
    IGNORE_DATASET_EXTERNAL_DTD = No
    INPUT_PORT_CONNECTED = CONNECTED
    MERGE_ATTRS = No
    NEW_ATTRIBUTES = complexType.complexContent.extension.sequence.element{}.name buffer complexType.complexContent.extension.sequence.element{}.type buffer complexType.complexContent.extension.sequence.element{}.nillable buffer complexType.complexContent.extension.sequence.element{}.maxOccurs buffer complexType.complexContent.extension.sequence.element{}.minOccurs buffer
    REJECT_FEATURES_WITH_NO_FRAGMENTS = YES
    XML_SOURCE_TYPE = xml_attr
    FRAGMENTS -> ListExploder_6
ListExploder_6
    ATTR_CONFLICT_RES_LOOKUP = INCOMING_IF_CONFLICT
    INDEX_ATTR = _element_index
    LIST_ATTR = complexType.complexContent.extension.sequence.element{}
    ATTR_ACCUM_MODE = Merge List Attributes
    ATTR_CONFLICT_RES = Use List Attribute Values
Note: DescribeFeatureType DAR navngivenvej
HTTPCaller_14
    AUTH_METHOD_TYPE = NC
    AUTH_NAMED_CONNECTION = DAF GraphQL API Key v1
    CLIENT_CERTIFICATE_TYPE = NONE
    CONNECTION_TIMEOUT_LENGTH = 60
    ERROR_ATTR = _error
    FOLLOW_REDIRECTS = FOLLOW_WITH_GET
    HTTP_METHOD = GET
    INPUT_PORT_CONNECTED = *
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://wfs.datafordeler.dk/DAR/DAR_WFS/1.0.0/WFS?service=WFS&version=2.0.0&request=DescribeFeatureType&typeName=navngivenvej_current
    TRANSFER_TIMEOUT_LENGTH = 90
    USE_COOKIES = No
    VERIFY_SSL_CERTIFICATES = Yes
    AUTH_METHOD = Web Connection
    -> XMLFragmenter_10
XMLFragmenter_10
    ATTRIBUTE_XML = _response_body
    DISABLE_EXTERNAL_ENTITY_PROCESSING = Yes
    EMBEDDED_EXPRESSIONS = schema
    ENTITY_RESOLVER = Yes
    FEATURE_TYPES_FORMAT_NAME = XML
    FLATTEN_OPTIONS = <structure separator="." map-empty-elements="yes" matched-prefix="attributes" matched-attributes="yes" cardinality="+{?}" structure-prefix="" child-position-attribute="" except-expression="" ui-mode="basic" matched-ancestor-attributes="" exclude-xml-fragment-attribute="yes"/>
    IGNORE_DATASET_EXTERNAL_DTD = No
    INPUT_PORT_CONNECTED = CONNECTED
    MERGE_ATTRS = No
    NEW_ATTRIBUTES = complexType.complexContent.extension.sequence.element{}.name buffer complexType.complexContent.extension.sequence.element{}.type buffer complexType.complexContent.extension.sequence.element{}.nillable buffer complexType.complexContent.extension.sequence.element{}.maxOccurs buffer complexType.complexContent.extension.sequence.element{}.minOccurs buffer
    REJECT_FEATURES_WITH_NO_FRAGMENTS = YES
    XML_SOURCE_TYPE = xml_attr
    FRAGMENTS -> ListExploder
ListExploder
    ATTR_CONFLICT_RES_LOOKUP = INCOMING_IF_CONFLICT
    INDEX_ATTR = _element_index
    LIST_ATTR = complexType.complexContent.extension.sequence.element{}
    ATTR_ACCUM_MODE = Merge List Attributes
    ATTR_CONFLICT_RES = Use List Attribute Values

Bookmark: 3.1 GetFeature
Note: GetFeature bygning_current
HTTPCaller_6
    AUTH_METHOD_TYPE = NC
    AUTH_NAMED_CONNECTION = DAF GraphQL API Key v1
    CLIENT_CERTIFICATE_TYPE = NONE
    CONNECTION_TIMEOUT_LENGTH = 120
    ERROR_ATTR = _error
    FOLLOW_REDIRECTS = FOLLOW_WITH_GET
    HTTP_METHOD = GET
    INPUT_PORT_CONNECTED = *
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://wfs.datafordeler.dk/GEODKV/GEODKV_WFS/1.0.0/WFS?request=GetFeature&TypeNames=bygning_current
    TRANSFER_TIMEOUT_LENGTH = 90
    USE_COOKIES = No
    VERIFY_SSL_CERTIFICATES = Yes
    AUTH_METHOD = Web Connection
    -> XMLFragmenter
XMLFragmenter
    ATTRIBUTE_XML = _response_body
    DISABLE_EXTERNAL_ENTITY_PROCESSING = Yes
    EMBEDDED_EXPRESSIONS = bygning_current
    ENTITY_RESOLVER = Yes
    FEATURE_TYPES_FORMAT_NAME = XML
    FLATTEN_OPTIONS = <structure separator="." map-empty-elements="yes" matched-prefix="attributes" matched-attributes="yes" cardinality="+{?}" structure-prefix="" child-position-attribute="" except-expression="" ui-mode="basic" matched-ancestor-attributes="" exclude-xml-fragment-attribute="yes"/>
    IGNORE_DATASET_EXTERNAL_DTD = No
    INPUT_PORT_CONNECTED = CONNECTED
    MERGE_ATTRS = No
    REJECT_FEATURES_WITH_NO_FRAGMENTS = YES
    XML_SOURCE_TYPE = xml_attr

FME custom transformer GraphQLtoJSON

Parameters:
- GQL =   # GraphQL

Input (input)
    -> Junction_19
Output (output)

Bookmark: 2.GraphQL string to JSON payload (secret sauce) 🕵
Junction_19
    -> ParameterFetcher
Note: Create _gql_rest attribute
ParameterFetcher
    ATTR_LIST = _gql $(GQL) _gql_rest $(GQL)
    -> StringReplacer
Note: Replace LF with \n
StringReplacer
    CASE = NO
    FIND_TEXT = "\n"
    NO_MATCH = _FME_NO_OP_
    REGEXP = NO
    REPLACE_TEXT = \n
    SRC_ATTRS = _gql_rest
    -> StringReplacer_2
StringReplacer_2
    CASE = NO
    FIND_TEXT = "
    NO_MATCH = _FME_NO_OP_
    REGEXP = NO
    REPLACE_TEXT = \"
    SRC_ATTRS = _gql_rest
    -> StringConcatenator
StringConcatenator
    ACTION = Create New Attribute
    PARM_LINE:
      fme_basicstring:22%17%22:{
        "query": "        @Value(_gql_rest)",
        "variables": {}
      }
    VAL_ATTR = _gql_rest
    -> Junction_20
Note: Escape " with \"
Note: Wrap in Json query and variables
Junction_20
    -> Junction
Junction
    -> Output (output)
