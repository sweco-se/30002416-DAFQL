FME workspace Demo_publish.fmw
Title: DAF2_demo_template_with_cache

Parameters:
- xmin = 555240
- ymin = 6322550
- xmax = 555700
- ymax = 6322900

Bookmark: Demo 1 - Schema
DAF2_SchemaInfo
    DAF_Flexible_URL = https://graphql.datafordeler.dk/flexible/v1/schema
    GetSchemaDataset = -
    GetSchemaForEntity = -

Bookmark: Demo 3 - Opret din egen GraphQL-forespørgsel ved hjælp af SWECO's Custom Transformer DAF2_SchemaInfo
Creator
    GEOMTYPE = Geometry Object
    NUM = 1
    CREATED -> ParameterFetcher
Note: Fetch parameters for bbox
ParameterFetcher
    ATTR_LIST = _xmin $(xmin) _ymin $(ymin) _xmax $(xmax) _ymax $(ymax)
    -> AttributeCreator
Note: Assign default for bbox if not given, and default VirkningFra and RegistreringFra to current datetime.
AttributeCreator
    ATTR_TABLE:
      SET_TO query.VirkningFra (varchar(200)) = FME_CONDITIONAL:DEFAULT_VALUE'_FME_NO_OP_'BOOL_OP;OR;COMPOSITE_TEST;1;TEST query.VirkningFra NOT_ATTRIBUTE_HAS_A_VALUE _FME_BLANK_STRING_'@DateTimeFormat(@DateTimeNow(),%Y-%m-%dT%H:%M:%SZ)'FME_NUM_CONDITIONS2___
      SET_TO query.RegistreringFra (varchar(200)) = FME_CONDITIONAL:DEFAULT_VALUE'_FME_NO_OP_'BOOL_OP;OR;COMPOSITE_TEST;1;TEST query.RegistreringFra NOT_ATTRIBUTE_HAS_A_VALUE _FME_BLANK_STRING_'@DateTimeFormat(@DateTimeNow(),%Y-%m-%dT%H:%M:%SZ)'FME_NUM_CONDITIONS2___
      SET_TO query.xmin (varchar(200)) = FME_CONDITIONAL:DEFAULT_VALUE'@Value(_xmin)'BOOL_OP;OR;COMPOSITE_TEST;1;TEST _xmin NOT_ATTRIBUTE_HAS_A_VALUE _FME_BLANK_STRING_'555000'FME_NUM_CONDITIONS2___
      SET_TO query.ymin (varchar(200)) = FME_CONDITIONAL:DEFAULT_VALUE'@Value(_ymin)'BOOL_OP;OR;COMPOSITE_TEST;1;TEST _ymin NOT_ATTRIBUTE_HAS_A_VALUE _FME_BLANK_STRING_'6322500'FME_NUM_CONDITIONS2___
      SET_TO query.xmax (varchar(200)) = FME_CONDITIONAL:DEFAULT_VALUE'@Value(_xmax)'BOOL_OP;OR;COMPOSITE_TEST;1;TEST _xmax NOT_ATTRIBUTE_HAS_A_VALUE _FME_BLANK_STRING_'556000'FME_NUM_CONDITIONS2___
      SET_TO query.ymax (varchar(200)) = FME_CONDITIONAL:DEFAULT_VALUE'@Value(_ymax)'BOOL_OP;OR;COMPOSITE_TEST;1;TEST _ymax NOT_ATTRIBUTE_HAS_A_VALUE _FME_BLANK_STRING_'6323000'FME_NUM_CONDITIONS2___
    -> AttributeCreator_2
Note: Create query
AttributeCreator_2
    ATTR_TABLE:
      SET_TO _gql (varchar(200)) = query {
            GEODKV_Bygning(
                virkningstid: "@Value(query.VirkningFra)"
                registreringstid: "@Value(query.RegistreringFra)"
                first: 200
                where: {
                    geometri: {
                        within: {
                            crs: 25832
                            wkt: "POLYGON((@Value(query.xmin) @Value(query.ymin), @Value(query.xmin) @Value(query.ymax), @Value(query.xmax) @Value(query.ymax), @Value(query.xmax) @Value(query.ymin), @Value(query.xmin) @Value(query.ymin)))"
                        }
                    }
                }
            ) {
            pageInfo {
              endCursor
              hasNextPage
            }
            nodes
                {
                applikation
                BBRaktion
                BBRUUID
                bygningstype
                dataansvar
                datafordelerOpdateringstid
                datafordelerRegisterImportSequenceNumber
                datafordelerRowId
                datafordelerRowVersion
                feltliste
                forretningshaendelse
                forretningsomraade
                forretningsproces
                geometri {
                    wkt
                    crs
                }
                geometristatus
                id_lokalId
                id_namespace
                kommentar
                maalestedBygning
                metode3D
                objectid
                overlapBygning
                planNoejagtighed
                planStedfaestelsesmetode
                registreringFra
                registreringsaktoer
                registreringsspecifikation
                registreringTil
                status
                synligBygning
                tempID
                underMinimumBygning
                vertikalNoejagtighed
                vertikalStedfaestelsesmetode
                virkningFra
                virkningsaktoer
                virkningTil
                referererTil {
                    datafordelerOpdateringstid
                    datafordelerRegisterImportSequenceNumber
                    datafordelerRowId
                    datafordelerRowVersion
                    ejerlejlighed
                    forretningshaendelse
                    forretningsomraade
                    forretningsproces
                    grund
                    husnummer
                    id_lokalId
                    id_namespace
                    jordstykke
                    kommunekode
                    registreringFra
                    registreringsaktoer
                    registreringTil
                    status
                    virkningFra
                    virkningsaktoer
                    virkningTil
                    husnummerBygning {
                        adgangsadressebetegnelse
                        adgangspunkt
                        adgangTilBygning
                        adgangTilTekniskAnlaeg
                        afstemningsomraade
                        datafordelerOpdateringstid
                        datafordelerRegisterImportSequenceNumber
                        datafordelerRowId
                        datafordelerRowVersion
                        forretningshaendelse
                        forretningsomraade
                        forretningsproces
                        geoDanmarkBygning
                        HusnummerHarAdgangspunkt {
                            datafordelerOpdateringstid
                            datafordelerRegisterImportSequenceNumber
                            datafordelerRowId
                            datafordelerRowVersion
                            forretningshaendelse
                            forretningsomraade
                            forretningsproces
                            id_lokalId
                            id_namespace
                            oprindelse_kilde
                            oprindelse_noejagtighedsklasse
                            oprindelse_registrering
                            oprindelse_tekniskStandard
                            position {
                                wkt
                                crs
                            }
                            registreringFra
                            registreringsaktoer
                            registreringTil
                            status
                            virkningFra
                            virkningsaktoer
                            virkningTil
                        }
                        husnummerHoererTilNavngivenVej {
                            administreresAfKommune
                            beskrivelse
                            datafordelerOpdateringstid
                            datafordelerRegisterImportSequenceNumber
                            datafordelerRowId
                            datafordelerRowVersion
                            forretningshaendelse
                            forretningsomraade
                            forretningsproces
                            id_lokalId
                            id_namespace
                            registreringFra
                            registreringsaktoer
                            registreringTil
                            status
                            udtaltVejnavn
                            vejadresseringsnavn
                            vejnavn
                            vejnavnebeliggenhed_oprindelse_kilde
                            vejnavnebeliggenhed_oprindelse_noejagtighedsklasse
                            vejnavnebeliggenhed_oprindelse_registrering
                            vejnavnebeliggenhed_oprindelse_tekniskStandard
                            vejnavnebeliggenhed_vejnavnelinje {
                                crs
                                wkt
                            }
                            vejnavnebeliggenhed_vejnavneomraade {
                                crs
                                wkt
                            }
                            vejnavnebeliggenhed_vejtilslutningspunkter {
                                crs
                                wkt
                            }
                            virkningFra
                            virkningsaktoer
                            virkningTil
                        }
                        husnummerretning {
                            wkt
                            crs
                        }
                        husnummertekst
                        id_lokalId
                        id_namespace
                        jordstykke
                        kommuneinddeling
                        menighedsraadsafstemningsomraade
                        navngivenVej
                        placeretPaaForeloebigtJordstykke
                        postnummer
                        registreringFra
                        registreringsaktoer
                        registreringTil
                        sogneinddeling
                        status
                        supplerendeBynavn
                        vejmidte
                        vejpunkt
                        virkningFra
                        virkningsaktoer
                        virkningTil
                    }

                }
                }
            }
        }
    -> StringReplacer_4
StringReplacer_4
    CASE = NO
    FIND_TEXT = virkningstid: "",<pipe>registreringstid: ""
    NO_MATCH = _FME_NO_OP_
    REGEXP = YES
    SRC_ATTRS = _gql
    -> Junction_3
Junction_3
    -> AttributeCopier_3
AttributeCopier_3
    ATTR_TABLE = COPY _gql > _gql_rest
    MISSING_INPUT_ATTRS = REMOVE
    -> StringReplacer_2
StringReplacer_2
    CASE = NO
    FIND_TEXT = "\n"
    NO_MATCH = _FME_NO_OP_
    REGEXP = NO
    REPLACE_TEXT = \n
    SRC_ATTRS = _gql_rest
    -> StringReplacer_3
StringReplacer_3
    CASE = NO
    FIND_TEXT = "
    NO_MATCH = _FME_NO_OP_
    REGEXP = NO
    REPLACE_TEXT = \"
    SRC_ATTRS = _gql_rest
    -> StringConcatenator_2
Note: Create query for sub-sequent fetches / Here it is crucial to add the following line after the line specifying number of fetched objects per iteration: / after: "@Value(pageInfo.endCursor)" / This tells the sub-sequent queries where in the result to continue fetching results, which will change for each iteration.
Note: Fetch sub-sequent pages of query results
StringConcatenator_2
    ACTION = Create New Attribute
    PARM_LINE:
      fme_basicstring:22%17%22:{
        "query": "        @Value(_gql_rest)",
        "variables": {}
      }
    VAL_ATTR = _gql_rest
    -> HTTPCaller_3
Note: Fetch page 1 of query results
HTTPCaller_3
    AUTH_METHOD_TYPE = NC
    AUTH_NAMED_CONNECTION = DAF GraphQL API Key v1
    CLIENT_CERTIFICATE_TYPE = NONE
    CONNECTION_TIMEOUT_LENGTH = 60
    CONTENT_TYPE_LOOKUP = application/json
    ERROR_ATTR = _error
    FOLLOW_REDIRECTS = FOLLOW_WITH_GET
    HTTP_METHOD = POST
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://graphql.datafordeler.dk/flexible/v1/
    TRANSFER_TIMEOUT_LENGTH = 90
    UPLOAD_BODY = @Value(_gql_rest)
    UPLOAD_TYPE = STRING_UPLOAD
    USE_COOKIES = No
    VERIFY_SSL_CERTIFICATES = Yes
    AUTH_METHOD = Web Connection
    UPLOAD_CONTENT_TYPE = JSON (application/json)
    -> JSONFragmenter_3
    -> JSONFragmenter_4
    <REJECTED> -> AttributeCreator_11
JSONFragmenter_3
    EXPLODE_FORMAT = JSON
    EXTRACT_ATTR = Yes
    JSON_ATTR = _response_body
    JSON_QUERY = json[*][*]
    NEW_ATTRIBUTES = nodes{} buffer pageInfo.endCursor buffer pageInfo.hasNextPage buffer
    READ_FROM_FILE = NO
    RECURSIVE = YES
    REJECT_EMPTY_LISTS = YES
    FRAGMENTS -> Tester
    <REJECTED> -> Junction
Note: Is there a next page?
Tester
    BOOL_OP = OR
    TEST_CLAUSE = TEST @Value(pageInfo.hasNextPage) = Yes
    TEST_MODE = TEST
    PASSED -> VariableSetter
    PASSED -> Junction_9
    FAILED -> Junction_9
Junction_9
    -> Junction_8
Junction_11
    -> Junction_8
Junction_8
    -> JSONFragmenter_5
Note: JSONFragmenter_2 : rejected
Junction_7
    -> Junction
Junction
    -> Junction_2
Junction_2
    -> AttributeCreator_13
Note: Create response as json for sending to an endpoint as a REST service.
Note: HTTPCaller_2 : <Rejected>
Junction_5
    -> AttributeCreator_11

Bookmark: Test first page results - and visualize Bygning, Adgangspunkt and NavngivenVej separately
JSONFragmenter_4
    EXPLODE_FORMAT = JSON
    EXTRACT_ATTR = Yes
    JSON_ATTR = _response_body
    JSON_QUERY = json["data"]["GEODKV_Bygning"]["nodes"][*]
    NEW_ATTRIBUTES = id_lokalId buffer referererTil.husnummerBygning.husnummerGiverAdgangTilTekniskAnlaeg buffer
    READ_FROM_FILE = NO
    RECURSIVE = YES
    REJECT_EMPTY_LISTS = YES
    FRAGMENTS -> AttributeRemover_2
AttributeRemover_2
    LIST_ATTRS = nodes{}
    -> AttributeExposer_2
AttributeExposer_2
    ATTR_TABLE = applikation,varchar(50),BBRaktion,varchar(17),BBRUUID,varchar(36),bygningstype,varchar(9),dataansvar,varchar(12),datafordelerOpdateringstid,varchar(27),datafordelerRegisterImportSequenceNumber,uint32,datafordelerRowId,varchar(36),datafordelerRowVersion,uint8,feltliste,varchar(200),forretningshaendelse,varchar(28),forretningsomraade,uint8,forretningsproces,varchar(28),geometri.crs,uint16,geometri.wkt,varchar(1475),geometristatus,varchar(10),id_lokalId,uint32,id_namespace,varchar(29),kommentar,varchar(25),maalestedBygning,varchar(12),metode3D,varchar(12),objectid,real64,overlapBygning,varchar(2),planNoejagtighed,real32,planStedfaestelsesmetode,varchar(13),referererTil,varchar(200),referererTil.byg007Bygningsnummer,uint8,referererTil.byg021BygningensAnvendelse,uint16,referererTil.byg024AntalLejlighederMedKoekken,varchar(200),referererTil.byg025AntalLejlighederUdenKoekken,varchar(200),referererTil.byg026Opfoerelsesaar,uint16,referererTil.byg027OmTilbygningsaar,uint16,referererTil.byg029DatoForMidlertidigOpfoertBygning,varchar(27),referererTil.byg030Vandforsyning,uint8,referererTil.byg031Afloebsforhold,uint8,referererTil.byg032YdervaeggensMateriale,uint8,referererTil.byg033Tagdaekningsmateriale,uint8,referererTil.byg034SupplerendeYdervaeggensMateriale,varchar(200),referererTil.byg035SupplerendeTagdaekningsMateriale,varchar(200),referererTil.byg036AsbestholdigtMateriale,varchar(200),referererTil.byg037KildeTilBygningensMaterialer,uint8,referererTil.byg038SamletBygningsareal,uint16,referererTil.byg039BygningensSamledeBoligAreal,uint16,referererTil.byg040BygningensSamledeErhvervsAreal,uint16,referererTil.byg041BebyggetAreal,uint16,referererTil.byg042ArealIndbyggetGarage,varchar(200),referererTil.byg043ArealIndbyggetCarport,varchar(200),referererTil.byg044ArealIndbyggetUdhus,uint8,referererTil.byg045ArealIndbyggetUdestueEllerLign,uint8,referererTil.byg046SamletArealAfLukkedeOverdaekningerPaaBygningen,varchar(200),referererTil.byg047ArealAfAffaldsrumITerraenniveau,varchar(200),referererTil.byg048AndetAreal,uint8,referererTil.byg049ArealAfOverdaekketAreal,uint8,referererTil.byg050ArealAabneOverdaekningerPaaBygningenSamlet,varchar(200),referererTil.byg051Adgangsareal,uint8,referererTil.byg052BeregningsprincipCarportAreal,varchar(200),referererTil.byg053BygningsarealerKilde,uint8,referererTil.byg054AntalEtager,uint8,referererTil.byg055AfvigendeEtager,uint8,referererTil.byg056Varmeinstallation,uint8,referererTil.byg057Opvarmningsmiddel,uint8,referererTil.byg058SupplerendeVarme,uint8,referererTil.byg069Sikringsrumpladser,uint16,referererTil.byg070Fredning,uint8,referererTil.byg071BevaringsvaerdighedReference,varchar(200),referererTil.byg094Revisionsdato,varchar(27),referererTil.byg111StormraadetsOversvoemmelsesSelvrisiko,varchar(200),referererTil.byg112DatoForRegistreringFraStormraadet,varchar(200),referererTil.byg113Byggeskadeforsikringsselskab,uint8,referererTil.byg114DatoForByggeskadeforsikring,varchar(27),referererTil.byg119Udledningstilladelse,varchar(200),referererTil.byg121OmfattetAfByggeskadeforsikring,uint8,referererTil.byg122Gyldighedsdato,varchar(27),referererTil.byg123MedlemskabAfSpildevandsforsyning,varchar(200),referererTil.byg124PaabudVedrSpildevandsafledning,varchar(200),referererTil.byg125FristVedrSpildevandsafledning,varchar(200),referererTil.byg126TilladelseTilUdtraeden,varchar(200),referererTil.byg127DatoForTilladelseTilUdtraeden,varchar(200),referererTil.byg128TilladelseTilAlternativBortskaffelseEllerAfledning,varchar(200),referererTil.byg129DatoForTilladelseTilAlternativBortskaffelseEllerAfledning,varchar(200),referererTil.byg130ArealAfUdvendigEfterisolering,varchar(200),referererTil.byg131DispensationFritagelseIftKollektivVarmeforsyning,varchar(200),referererTil.byg132DatoForDispensationFritagelseIftKollektivVarmeforsyning,varchar(200),referererTil.byg133KildeTilKoordinatsaet,varchar(1),referererTil.byg134KvalitetAfKoordinatsaet,uint8,referererTil.byg135SupplerendeOplysningOmKoordinatsaet,uint8,referererTil.byg136PlaceringPaaSoeterritorie,uint8,referererTil.byg137BanedanmarkBygvaerksnummer,varchar(200),referererTil.byg140ServitutForUdlejningsEjendomDato,varchar(200),referererTil.byg150Gulvbelaegning,varchar(200),referererTil.byg151Frihoejde,varchar(200),referererTil.byg152AabenLukketKonstruktion,varchar(200),referererTil.byg153Konstruktionsforhold,varchar(200),referererTil.byg301TypeAfFlytning,varchar(200),referererTil.byg302Tilflytterkommune,varchar(200),referererTil.byg403OevrigeBemaerkningerFraStormraadet,varchar(200),referererTil.byg404Koordinat.crs,uint16,referererTil.byg404Koordinat.wkt,varchar(28),referererTil.byg406Koordinatsystem,uint8,referererTil.byg500Notatlinjer,varchar(200),referererTil.bygningEjerlejlighed,varchar(200),referererTil.bygningEjerlejlighed.ejendommensEjerforholdskode,uint8,referererTil.bygningEjerlejlighed.ejendomsnummer,uint32,referererTil.bygningEjerlejlighed.ejendomstype,uint8,referererTil.bygningEjerlejlighed.ejerlejlighed,uint32,referererTil.bygningEjerlejlighed.ejerlejlighedsnummer,uint8,referererTil.bygningEjerlejlighed.id_lokalId,varchar(36),referererTil.bygningEjerlejlighed.id_namespace,varchar(39),referererTil.bygningEjerlejlighed.kommunekode,uint16,referererTil.bygningEjerlejlighed.registreringFra,varchar(27),referererTil.bygningEjerlejlighed.registreringsaktoer,varchar(3),referererTil.bygningEjerlejlighed.registreringTil,varchar(200),referererTil.bygningEjerlejlighed.samletFastEjendom,varchar(200),referererTil.bygningEjerlejlighed.status,uint8,referererTil.bygningEjerlejlighed.tinglystAreal,uint8,referererTil.bygningEjerlejlighed.virkningFra,varchar(27),referererTil.bygningEjerlejlighed.virkningsaktoer,varchar(3),referererTil.bygningEjerlejlighed.virkningTil,varchar(200),referererTil.bygningEjerlejlighed.vurderingsejendomsnummer,varchar(200),referererTil.bygningGrund.bestemtFastEjendom,varchar(36),referererTil.bygningGrund.datafordelerOpdateringstid,varchar(27),referererTil.bygningGrund.datafordelerRegisterImportSequenceNumber,uint32,referererTil.bygningGrund.datafordelerRowId,varchar(36),referererTil.bygningGrund.datafordelerRowVersion,uint8,referererTil.bygningGrund.forretningshaendelse,varchar(5),referererTil.bygningGrund.forretningsomraade,varchar(11),referererTil.bygningGrund.forretningsproces,uint8,referererTil.bygningGrund.gru009Vandforsyning,uint8,referererTil.bygningGrund.gru010Afloebsforhold,uint8,referererTil.bygningGrund.gru021Udledningstilladelse,varchar(200),referererTil.bygningGrund.gru022MedlemskabAfSpildevandsforsyning,varchar(200),referererTil.bygningGrund.gru023PaabudVedrSpildevandsafledning,uint8,referererTil.bygningGrund.gru024FristVedrSpildevandsafledning,varchar(27),referererTil.bygningGrund.gru025TilladelseTilUdtraeden,varchar(200),referererTil.bygningGrund.gru026DatoForTilladelseTilUdtraeden,varchar(200),referererTil.bygningGrund.gru027TilladelseTilAlternativBortskaffelseEllerAfledning,varchar(200),referererTil.bygningGrund.gru028DatoForTilladelseTilAlternativBortskaffelseEllerAfledning,varchar(200),referererTil.bygningGrund.gru029DispensationFritagelseIftKollektivVarmeforsyning,varchar(200),referererTil.bygningGrund.gru030DatoForDispensationFritagelseIftKollektivVarmeforsyning,varchar(200),referererTil.bygningGrund.gru500Notatlinjer,varchar(200),referererTil.bygningGrund.husnummer,varchar(36),referererTil.bygningGrund.id_lokalId,varchar(36),referererTil.bygningGrund.id_namespace,varchar(28),referererTil.bygningGrund.kommunekode,uint16,referererTil.bygningGrund.registreringFra,varchar(27),referererTil.bygningGrund.registreringsaktoer,varchar(3),referererTil.bygningGrund.registreringTil,varchar(200),referererTil.bygningGrund.status,uint8,referererTil.bygningGrund.virkningFra,varchar(27),referererTil.bygningGrund.virkningsaktoer,varchar(16),referererTil.bygningGrund.virkningTil,varchar(200),referererTil.datafordelerOpdateringstid,varchar(27),referererTil.datafordelerRegisterImportSequenceNumber,uint32,referererTil.datafordelerRowId,varchar(36),referererTil.datafordelerRowVersion,uint8,referererTil.ejerlejlighed,varchar(36),referererTil.forretningshaendelse,varchar(7),referererTil.forretningsomraade,varchar(11),referererTil.forretningsproces,uint8,referererTil.grund,varchar(36),referererTil.husnummer,varchar(36),referererTil.husnummerBygning.adgangsadressebetegnelse,varchar(39),referererTil.husnummerBygning.adgangspunkt,varchar(36),referererTil.husnummerBygning.adgangTilBygning,varchar(36),referererTil.husnummerBygning.adgangTilTekniskAnlaeg,varchar(200),referererTil.husnummerBygning.afstemningsomraade,uint32,referererTil.husnummerBygning.datafordelerOpdateringstid,varchar(27),referererTil.husnummerBygning.datafordelerRegisterImportSequenceNumber,uint32,referererTil.husnummerBygning.datafordelerRowId,varchar(36),referererTil.husnummerBygning.datafordelerRowVersion,uint8,referererTil.husnummerBygning.forretningshaendelse,uint8,referererTil.husnummerBygning.forretningsomraade,varchar(11),referererTil.husnummerBygning.forretningsproces,uint8,referererTil.husnummerBygning.geoDanmarkBygning,uint32,referererTil.husnummerBygning.husnummerretning.crs,uint16,referererTil.husnummerBygning.husnummerretning.wkt,varchar(45),referererTil.husnummerBygning.husnummertekst,varchar(3),referererTil.husnummerBygning.id_lokalId,varchar(36),referererTil.husnummerBygning.id_namespace,varchar(32),referererTil.husnummerBygning.jordstykke,uint32,referererTil.husnummerBygning.kommuneinddeling,uint32,referererTil.husnummerBygning.menighedsraadsafstemningsomraade,uint32,referererTil.husnummerBygning.navngivenVej,varchar(36),referererTil.husnummerBygning.placeretPaaForeloebigtJordstykke,varchar(200),referererTil.husnummerBygning.postnummer,varchar(36),referererTil.husnummerBygning.registreringFra,varchar(27),referererTil.husnummerBygning.registreringsaktoer,varchar(3),referererTil.husnummerBygning.registreringTil,varchar(200),referererTil.husnummerBygning.sogneinddeling,uint32,referererTil.husnummerBygning.status,uint8,referererTil.husnummerBygning.supplerendeBynavn,varchar(200),referererTil.husnummerBygning.vejmidte,varchar(9),referererTil.husnummerBygning.vejpunkt,varchar(36),referererTil.husnummerBygning.virkningFra,varchar(27),referererTil.husnummerBygning.virkningsaktoer,varchar(39),referererTil.husnummerBygning.virkningTil,varchar(200),referererTil.id_lokalId,varchar(36),referererTil.id_namespace,varchar(30),referererTil.jordstykke,uint32,referererTil.kommunekode,uint16,referererTil.registreringFra,varchar(27),referererTil.registreringsaktoer,varchar(3),referererTil.registreringTil,varchar(200),referererTil.status,uint8,referererTil.virkningFra,varchar(27),referererTil.virkningsaktoer,varchar(16),referererTil.virkningTil,varchar(200),registreringFra,varchar(27),registreringsaktoer,varchar(31),registreringsspecifikation,varchar(19),registreringTil,varchar(200),status,varchar(18),synligBygning,varchar(3),tempID,varchar(200),underMinimumBygning,varchar(3),vertikalNoejagtighed,real32,vertikalStedfaestelsesmetode,varchar(13),virkningFra,varchar(27),virkningsaktoer,varchar(31),virkningTil,varchar(200),referererTil.husnummerBygning.HusnummerHarAdgangspunkt.position.wkt,,referererTil.husnummerBygning.HusnummerHarAdgangspunkt.id_lokalId,,referererTil.husnummerBygning.HusnummerHarAdgangspunkt.datafordelerOpdateringstid,,referererTil.husnummerBygning.HusnummerHarAdgangspunkt.id_namespace,,referererTil.husnummerBygning.HusnummerHarAdgangspunkt.oprindelse_kilde,,referererTil.husnummerBygning.HusnummerHarAdgangspunkt.oprindelse_noejagtighedsklasse,,referererTil.husnummerBygning.HusnummerHarAdgangspunkt.position.crs,,referererTil.husnummerBygning.HusnummerHarAdgangspunkt.registreringFra,,referererTil.husnummerBygning.HusnummerHarAdgangspunkt.registreringTil,,referererTil.husnummerBygning.HusnummerHarAdgangspunkt.status,,referererTil.husnummerBygning.HusnummerHarAdgangspunkt.virkningFra,,referererTil.husnummerBygning.HusnummerHarAdgangspunkt.virkningTil,,referererTil.husnummerBygning.husnummerHoererTilNavngivenVej.administreresAfKommune,,referererTil.husnummerBygning.husnummerHoererTilNavngivenVej.beskrivelse,,referererTil.husnummerBygning.husnummerHoererTilNavngivenVej.id_lokalId,,referererTil.husnummerBygning.husnummerHoererTilNavngivenVej.id_namespace,,referererTil.husnummerBygning.husnummerHoererTilNavngivenVej.registreringFra,,referererTil.husnummerBygning.husnummerHoererTilNavngivenVej.registreringsaktoer,,referererTil.husnummerBygning.husnummerHoererTilNavngivenVej.registreringTil,,referererTil.husnummerBygning.husnummerHoererTilNavngivenVej.status,,referererTil.husnummerBygning.husnummerHoererTilNavngivenVej.udtaltVejnavn,,referererTil.husnummerBygning.husnummerHoererTilNavngivenVej.vejadresseringsnavn,,referererTil.husnummerBygning.husnummerHoererTilNavngivenVej.vejnavn,,referererTil.husnummerBygning.husnummerHoererTilNavngivenVej.vejnavnebeliggenhed_oprindelse_kilde,,referererTil.husnummerBygning.husnummerHoererTilNavngivenVej.vejnavnebeliggenhed_vejnavnelinje.crs,,referererTil.husnummerBygning.husnummerHoererTilNavngivenVej.vejnavnebeliggenhed_vejnavnelinje.wkt,,referererTil.husnummerBygning.husnummerHoererTilNavngivenVej.virkningFra,,referererTil.husnummerBygning.husnummerHoererTilNavngivenVej.virkningTil,
    -> AttributeCreator_4
AttributeCreator_4
    ATTR_TABLE = SET_TO _coordsys (varchar(200)) = EPSG:@Value(geometri.crs)
    -> CoordinateSystemSetter_3
CoordinateSystemSetter_3
    COORDSYS = @Value(_coordsys)
    -> AttributeKeeper_4
    -> AttributeKeeper
    -> AttributeKeeper_3
AttributeKeeper_4
    CREATE_BULK_MODE_FEATURES = NO
    KEEP_ATTRS = BBRUUID,BBRaktion,applikation,bygningstype,dataansvar,datafordelerOpdateringstid,datafordelerRegisterImportSequenceNumber,datafordelerRowId,datafordelerRowVersion,feltliste,forretningshaendelse,forretningsomraade,forretningsproces,geometri.crs,geometri.wkt,geometristatus,id_lokalId,id_namespace,kommentar,maalestedBygning,metode3D,objectid,overlapBygning,planNoejagtighed,planStedfaestelsesmetode,referererTil.byg007Bygningsnummer,referererTil.byg021BygningensAnvendelse,referererTil.byg024AntalLejlighederMedKoekken,referererTil.byg025AntalLejlighederUdenKoekken,referererTil.byg026Opfoerelsesaar,referererTil.byg027OmTilbygningsaar,referererTil.byg029DatoForMidlertidigOpfoertBygning,referererTil.byg030Vandforsyning,referererTil.byg031Afloebsforhold,referererTil.byg032YdervaeggensMateriale,referererTil.byg033Tagdaekningsmateriale,referererTil.byg034SupplerendeYdervaeggensMateriale,referererTil.byg035SupplerendeTagdaekningsMateriale,referererTil.byg036AsbestholdigtMateriale,referererTil.byg037KildeTilBygningensMaterialer,referererTil.byg038SamletBygningsareal,referererTil.byg039BygningensSamledeBoligAreal,referererTil.byg040BygningensSamledeErhvervsAreal,referererTil.byg041BebyggetAreal,referererTil.byg042ArealIndbyggetGarage,referererTil.byg043ArealIndbyggetCarport,referererTil.byg044ArealIndbyggetUdhus,referererTil.byg045ArealIndbyggetUdestueEllerLign,referererTil.byg046SamletArealAfLukkedeOverdaekningerPaaBygningen,referererTil.byg047ArealAfAffaldsrumITerraenniveau,referererTil.byg048AndetAreal,referererTil.byg049ArealAfOverdaekketAreal,referererTil.byg050ArealAabneOverdaekningerPaaBygningenSamlet,referererTil.byg051Adgangsareal,referererTil.byg052BeregningsprincipCarportAreal,referererTil.byg053BygningsarealerKilde,referererTil.byg054AntalEtager,referererTil.byg055AfvigendeEtager,referererTil.byg056Varmeinstallation,referererTil.byg057Opvarmningsmiddel,referererTil.byg058SupplerendeVarme,referererTil.byg069Sikringsrumpladser,referererTil.byg070Fredning,referererTil.byg071BevaringsvaerdighedReference,referererTil.byg094Revisionsdato,referererTil.byg111StormraadetsOversvoemmelsesSelvrisiko,referererTil.byg112DatoForRegistreringFraStormraadet,referererTil.byg113Byggeskadeforsikringsselskab,referererTil.byg114DatoForByggeskadeforsikring,referererTil.byg119Udledningstilladelse,referererTil.byg121OmfattetAfByggeskadeforsikring,referererTil.byg122Gyldighedsdato,referererTil.byg123MedlemskabAfSpildevandsforsyning,referererTil.byg124PaabudVedrSpildevandsafledning,referererTil.byg125FristVedrSpildevandsafledning,referererTil.byg126TilladelseTilUdtraeden,referererTil.byg127DatoForTilladelseTilUdtraeden,referererTil.byg128TilladelseTilAlternativBortskaffelseEllerAfledning,referererTil.byg129DatoForTilladelseTilAlternativBortskaffelseEllerAfledning,referererTil.byg130ArealAfUdvendigEfterisolering,referererTil.byg131DispensationFritagelseIftKollektivVarmeforsyning,referererTil.byg132DatoForDispensationFritagelseIftKollektivVarmeforsyning,referererTil.byg133KildeTilKoordinatsaet,referererTil.byg134KvalitetAfKoordinatsaet,referererTil.byg135SupplerendeOplysningOmKoordinatsaet,referererTil.byg136PlaceringPaaSoeterritorie,referererTil.byg137BanedanmarkBygvaerksnummer,referererTil.byg140ServitutForUdlejningsEjendomDato,referererTil.byg150Gulvbelaegning,referererTil.byg151Frihoejde,referererTil.byg152AabenLukketKonstruktion,referererTil.byg153Konstruktionsforhold,referererTil.byg301TypeAfFlytning,referererTil.byg302Tilflytterkommune,referererTil.byg403OevrigeBemaerkningerFraStormraadet,referererTil.byg404Koordinat.crs,referererTil.byg404Koordinat.wkt,referererTil.byg406Koordinatsystem,referererTil.byg500Notatlinjer,referererTil.bygningEjerlejlighed,referererTil.bygningEjerlejlighed.ejendommensEjerforholdskode,referererTil.bygningEjerlejlighed.ejendomsnummer,referererTil.bygningEjerlejlighed.ejendomstype,referererTil.bygningEjerlejlighed.ejerlejlighed,referererTil.bygningEjerlejlighed.ejerlejlighedsnummer,referererTil.bygningEjerlejlighed.id_lokalId,referererTil.bygningEjerlejlighed.id_namespace,referererTil.bygningEjerlejlighed.kommunekode,referererTil.bygningEjerlejlighed.registreringFra,referererTil.bygningEjerlejlighed.registreringTil,referererTil.bygningEjerlejlighed.registreringsaktoer,referererTil.bygningEjerlejlighed.samletFastEjendom,referererTil.bygningEjerlejlighed.status,referererTil.bygningEjerlejlighed.tinglystAreal,referererTil.bygningEjerlejlighed.virkningFra,referererTil.bygningEjerlejlighed.virkningTil,referererTil.bygningEjerlejlighed.virkningsaktoer,referererTil.bygningEjerlejlighed.vurderingsejendomsnummer,referererTil.bygningGrund.bestemtFastEjendom,referererTil.bygningGrund.datafordelerOpdateringstid,referererTil.bygningGrund.datafordelerRegisterImportSequenceNumber,referererTil.bygningGrund.datafordelerRowId,referererTil.bygningGrund.datafordelerRowVersion,referererTil.bygningGrund.forretningshaendelse,referererTil.bygningGrund.forretningsomraade,referererTil.bygningGrund.forretningsproces,referererTil.bygningGrund.gru009Vandforsyning,referererTil.bygningGrund.gru010Afloebsforhold,referererTil.bygningGrund.gru021Udledningstilladelse,referererTil.bygningGrund.gru022MedlemskabAfSpildevandsforsyning,referererTil.bygningGrund.gru023PaabudVedrSpildevandsafledning,referererTil.bygningGrund.gru024FristVedrSpildevandsafledning,referererTil.bygningGrund.gru025TilladelseTilUdtraeden,referererTil.bygningGrund.gru026DatoForTilladelseTilUdtraeden,referererTil.bygningGrund.gru027TilladelseTilAlternativBortskaffelseEllerAfledning,referererTil.bygningGrund.gru028DatoForTilladelseTilAlternativBortskaffelseEllerAfledning,referererTil.bygningGrund.gru029DispensationFritagelseIftKollektivVarmeforsyning,referererTil.bygningGrund.gru030DatoForDispensationFritagelseIftKollektivVarmeforsyning,referererTil.bygningGrund.gru500Notatlinjer,referererTil.bygningGrund.husnummer,referererTil.bygningGrund.id_lokalId,referererTil.bygningGrund.id_namespace,referererTil.bygningGrund.kommunekode,referererTil.bygningGrund.registreringFra,referererTil.bygningGrund.registreringTil,referererTil.bygningGrund.registreringsaktoer,referererTil.bygningGrund.status,referererTil.bygningGrund.virkningFra,referererTil.bygningGrund.virkningTil,referererTil.bygningGrund.virkningsaktoer,referererTil.datafordelerOpdateringstid,referererTil.datafordelerRegisterImportSequenceNumber,referererTil.datafordelerRowId,referererTil.datafordelerRowVersion,referererTil.ejerlejlighed,referererTil.forretningshaendelse,referererTil.forretningsomraade,referererTil.forretningsproces,referererTil.grund,referererTil.husnummer,referererTil.husnummerBygning.adgangTilBygning,referererTil.husnummerBygning.adgangTilTekniskAnlaeg,referererTil.husnummerBygning.adgangsadressebetegnelse,referererTil.husnummerBygning.adgangspunkt,referererTil.husnummerBygning.afstemningsomraade,referererTil.husnummerBygning.datafordelerOpdateringstid,referererTil.husnummerBygning.datafordelerRegisterImportSequenceNumber,referererTil.husnummerBygning.datafordelerRowId,referererTil.husnummerBygning.datafordelerRowVersion,referererTil.husnummerBygning.forretningshaendelse,referererTil.husnummerBygning.forretningsomraade,referererTil.husnummerBygning.forretningsproces,referererTil.husnummerBygning.geoDanmarkBygning,referererTil.husnummerBygning.husnummerGiverAdgangTilTekniskAnlaeg,referererTil.husnummerBygning.husnummerretning.crs,referererTil.husnummerBygning.husnummerretning.wkt,referererTil.husnummerBygning.husnummertekst,referererTil.husnummerBygning.id_lokalId,referererTil.husnummerBygning.id_namespace,referererTil.husnummerBygning.jordstykke,referererTil.husnummerBygning.kommuneinddeling,referererTil.husnummerBygning.menighedsraadsafstemningsomraade,referererTil.husnummerBygning.navngivenVej,referererTil.husnummerBygning.placeretPaaForeloebigtJordstykke,referererTil.husnummerBygning.postnummer,referererTil.husnummerBygning.registreringFra,referererTil.husnummerBygning.registreringTil,referererTil.husnummerBygning.registreringsaktoer,referererTil.husnummerBygning.sogneinddeling,referererTil.husnummerBygning.status,referererTil.husnummerBygning.supplerendeBynavn,referererTil.husnummerBygning.vejmidte,referererTil.husnummerBygning.vejpunkt,referererTil.husnummerBygning.virkningFra,referererTil.husnummerBygning.virkningTil,referererTil.husnummerBygning.virkningsaktoer,referererTil.id_lokalId,referererTil.id_namespace,referererTil.jordstykke,referererTil.kommunekode,referererTil.registreringFra,referererTil.registreringTil,referererTil.registreringsaktoer,referererTil.status,referererTil.virkningFra,referererTil.virkningTil,referererTil.virkningsaktoer,registreringFra,registreringTil,registreringsaktoer,registreringsspecifikation,status,synligBygning,tempID,underMinimumBygning,vertikalNoejagtighed,vertikalStedfaestelsesmetode,virkningFra,virkningTil,virkningsaktoer
    -> AttributeCreator_3
AttributeCreator_3
    ATTR_TABLE = SET_TO _crs_ogc (varchar(200)) = urn:ogc:def:crs:EPSG::@Value(geometri.crs)
    -> GeometryReplacer_2
Note: Bygningspolygoner with attributes from BBR_Bygning and DAR_Husnummer
GeometryReplacer_2
    KIND = wkt
    OGC_WKT_PRECISION = FLOAT_64
    REMOVE_ATTRIBUTE = No
    SOURCE = @Value(geometri.wkt)
    KIND_LONG = OGC Well Known Text
    OGC_WKT_PRECISION_DISPLAY = 64-bit
AttributeKeeper
    CREATE_BULK_MODE_FEATURES = NO
    KEEP_ATTRS = referererTil.husnummerBygning.HusnummerHarAdgangspunkt.position.wkt,referererTil.husnummerBygning.HusnummerHarAdgangspunkt.datafordelerOpdateringstid,referererTil.husnummerBygning.HusnummerHarAdgangspunkt.id_lokalId,referererTil.husnummerBygning.HusnummerHarAdgangspunkt.id_namespace,referererTil.husnummerBygning.HusnummerHarAdgangspunkt.oprindelse_kilde,referererTil.husnummerBygning.HusnummerHarAdgangspunkt.oprindelse_noejagtighedsklasse,referererTil.husnummerBygning.HusnummerHarAdgangspunkt.position.crs,referererTil.husnummerBygning.HusnummerHarAdgangspunkt.registreringFra,referererTil.husnummerBygning.HusnummerHarAdgangspunkt.registreringTil,referererTil.husnummerBygning.HusnummerHarAdgangspunkt.status,referererTil.husnummerBygning.HusnummerHarAdgangspunkt.virkningFra,referererTil.husnummerBygning.HusnummerHarAdgangspunkt.virkningTil
    -> AttributeCreator_6
AttributeCreator_6
    ATTR_TABLE = SET_TO _crs_ogc (varchar(200)) = urn:ogc:def:crs:EPSG::@Value(referererTil.husnummerBygning.HusnummerHarAdgangspunkt.position.crs)
    -> GeometryReplacer_4
Note: Adgangspunkt
GeometryReplacer_4
    KIND = wkt
    OGC_WKT_PRECISION = FLOAT_64
    REMOVE_ATTRIBUTE = Yes
    SOURCE = @Value(referererTil.husnummerBygning.HusnummerHarAdgangspunkt.position.wkt)
    KIND_LONG = OGC Well Known Text
    OGC_WKT_PRECISION_DISPLAY = 64-bit
AttributeKeeper_3
    CREATE_BULK_MODE_FEATURES = NO
    KEEP_ATTRS = referererTil.husnummerBygning.husnummerHoererTilNavngivenVej.administreresAfKommune,referererTil.husnummerBygning.husnummerHoererTilNavngivenVej.beskrivelse,referererTil.husnummerBygning.husnummerHoererTilNavngivenVej.id_lokalId,referererTil.husnummerBygning.husnummerHoererTilNavngivenVej.id_namespace,referererTil.husnummerBygning.husnummerHoererTilNavngivenVej.registreringFra,referererTil.husnummerBygning.husnummerHoererTilNavngivenVej.registreringTil,referererTil.husnummerBygning.husnummerHoererTilNavngivenVej.registreringsaktoer,referererTil.husnummerBygning.husnummerHoererTilNavngivenVej.status,referererTil.husnummerBygning.husnummerHoererTilNavngivenVej.udtaltVejnavn,referererTil.husnummerBygning.husnummerHoererTilNavngivenVej.vejadresseringsnavn,referererTil.husnummerBygning.husnummerHoererTilNavngivenVej.vejnavn,referererTil.husnummerBygning.husnummerHoererTilNavngivenVej.vejnavnebeliggenhed_oprindelse_kilde,referererTil.husnummerBygning.husnummerHoererTilNavngivenVej.vejnavnebeliggenhed_vejnavnelinje.crs,referererTil.husnummerBygning.husnummerHoererTilNavngivenVej.vejnavnebeliggenhed_vejnavnelinje.wkt,referererTil.husnummerBygning.husnummerHoererTilNavngivenVej.virkningFra,referererTil.husnummerBygning.husnummerHoererTilNavngivenVej.virkningTil
    -> AttributeCreator_7
AttributeCreator_7
    ATTR_TABLE = SET_TO _crs_ogc (varchar(200)) = urn:ogc:def:crs:EPSG::@Value(referererTil.husnummerBygning.husnummerHoererTilNavngivenVej.vejnavnebeliggenhed_vejnavnelinje.crs)
    -> GeometryReplacer_5
Note: NavngivenVej
GeometryReplacer_5
    KIND = wkt
    OGC_WKT_PRECISION = FLOAT_64
    REMOVE_ATTRIBUTE = Yes
    SOURCE = @Value(referererTil.husnummerBygning.husnummerHoererTilNavngivenVej.vejnavnebeliggenhed_vejnavnelinje.wkt)
    KIND_LONG = OGC Well Known Text
    OGC_WKT_PRECISION_DISPLAY = 64-bit

Bookmark: 3. Set up global variable and clone max number of calls. Secret sauce.
Note: Global variable vEndCursor / has the next cursor
VariableSetter
    SCOPE = Global
    VALUE = @Value(pageInfo.endCursor)
    VARNAME = vEndCursor
    -> Cloner
Note: Max 19 calls here => 20 total. / Possibly 4000 records
Cloner
    COPIES = 19
    COPYATT = _copynum
    COPY -> VariableRetriever
Note: Look ahead for new cursor in global variable
VariableRetriever
    SCOPE = Global
    VALUE_ATTR = _v_cursor
    VARNAME = vEndCursor
    -> Tester_9
    <REJECTED> -> Junction
Note: Last page?
Tester_9
    BOOL_OP = OR
    TEST_CLAUSE = TEST @Value(_v_cursor) != lastpage
    TEST_MODE = TEST
    PASSED -> AttributeCreator_8

Bookmark: 4. Prepare modified GraphQL by inserting cursor for consecutive calls
AttributeCreator_8
    ATTR_TABLE:
      SET_TO _gql (varchar(200)) =
        query {
            GEODKV_Bygning(
                virkningstid: "@Value(query.VirkningFra)",
                registreringstid: "@Value(query.RegistreringFra)"
                first: 200
                after: "@Value(pageInfo.endCursor)"
                where: {
                    geometri: {
                        within: {
                            crs: 25832
                            wkt: "MULTIPOLYGON (((@Value(query.xmin) @Value(query.ymin), @Value(query.xmin) @Value(query.ymax), @Value(query.xmax) @Value(query.ymax), @Value(query.xmax) @Value(query.ymin), @Value(query.xmin) @Value(query.ymin))))"
                        }
                    }
                }
            ) {
            pageInfo {
              endCursor
              hasNextPage
            }
            nodes
                {
                applikation
                BBRaktion
                BBRUUID
                bygningstype
                dataansvar
                datafordelerOpdateringstid
                datafordelerRegisterImportSequenceNumber
                datafordelerRowId
                datafordelerRowVersion
                feltliste
                forretningshaendelse
                forretningsomraade
                forretningsproces
                geometri {
                    wkt
                    crs
                }
                geometristatus
                id_lokalId
                id_namespace
                kommentar
                maalestedBygning
                metode3D
                objectid
                overlapBygning
                planNoejagtighed
                planStedfaestelsesmetode
                referererTil {
                    bygningEjerlejlighed {
                        id_lokalId
                        ejerlejlighed
                        ejendommensEjerforholdskode
                        ejendomsnummer
                        ejendomstype
                        ejerlejlighed
                        ejerlejlighedsnummer
                        id_namespace
                        kommunekode
                        registreringFra
                        registreringsaktoer
                        registreringTil
                        samletFastEjendom
                        status
                        tinglystAreal
                        virkningFra
                        virkningsaktoer
                        virkningTil
                        vurderingsejendomsnummer
                    }
                    bygningGrund {
                        bestemtFastEjendom
                        datafordelerOpdateringstid
                        datafordelerRegisterImportSequenceNumber
                        datafordelerRowId
                        datafordelerRowVersion
                        forretningshaendelse
                        forretningsomraade
                        forretningsproces
                        gru009Vandforsyning
                        gru010Afloebsforhold
                        gru021Udledningstilladelse
                        gru022MedlemskabAfSpildevandsforsyning
                        gru023PaabudVedrSpildevandsafledning
                        gru024FristVedrSpildevandsafledning
                        gru025TilladelseTilUdtraeden
                        gru026DatoForTilladelseTilUdtraeden
                        gru027TilladelseTilAlternativBortskaffelseEllerAfledning
                        gru028DatoForTilladelseTilAlternativBortskaffelseEllerAfledning
                        gru029DispensationFritagelseIftKollektivVarmeforsyning
                        gru030DatoForDispensationFritagelseIftKollektivVarmeforsyning
                        gru500Notatlinjer
                        husnummer
                        id_lokalId
                        id_namespace
                        kommunekode
                        registreringFra
                        registreringsaktoer
                        registreringTil
                        status
                        virkningFra
                        virkningsaktoer
                        virkningTil
                    }
                    husnummerBygning {
                        adgangsadressebetegnelse
                        HusnummerHarAdgangspunkt {
                            id_lokalId
                            id_namespace
                            position {
                                    wkt
                                    crs
                                    type
                                    dimension
                            }
                            registreringFra
                            status
                            virkningFra
                        }
                        adgangspunkt
                        adgangTilBygning
                        adgangTilTekniskAnlaeg
                        afstemningsomraade
                        datafordelerOpdateringstid
                        datafordelerRegisterImportSequenceNumber
                        datafordelerRowId
                        datafordelerRowVersion
                        forretningshaendelse
                        forretningsomraade
                        forretningsproces
                        geoDanmarkBygning
                        husnummerretning {
                            wkt
                            crs
                        }
                        husnummertekst
                        id_lokalId
                        id_namespace
                        jordstykke
                        kommuneinddeling
                        menighedsraadsafstemningsomraade
                        navngivenVej
                        placeretPaaForeloebigtJordstykke
                        postnummer
                        registreringFra
                        registreringsaktoer
                        registreringTil
                        sogneinddeling
                        status
                        supplerendeBynavn
                        vejmidte
                        vejpunkt
                        virkningFra
                        virkningsaktoer
                        virkningTil
                    }
                    byg007Bygningsnummer
                    byg021BygningensAnvendelse
                    byg024AntalLejlighederMedKoekken
                    byg025AntalLejlighederUdenKoekken
                    byg026Opfoerelsesaar
                    byg027OmTilbygningsaar
                    byg029DatoForMidlertidigOpfoertBygning
                    byg030Vandforsyning
                    byg031Afloebsforhold
                    byg032YdervaeggensMateriale
                    byg033Tagdaekningsmateriale
                    byg034SupplerendeYdervaeggensMateriale
                    byg035SupplerendeTagdaekningsMateriale
                    byg036AsbestholdigtMateriale
                    byg037KildeTilBygningensMaterialer
                    byg038SamletBygningsareal
                    byg039BygningensSamledeBoligAreal
                    byg040BygningensSamledeErhvervsAreal
                    byg041BebyggetAreal
                    byg042ArealIndbyggetGarage
                    byg043ArealIndbyggetCarport
                    byg044ArealIndbyggetUdhus
                    byg045ArealIndbyggetUdestueEllerLign
                    byg046SamletArealAfLukkedeOverdaekningerPaaBygningen
                    byg047ArealAfAffaldsrumITerraenniveau
                    byg048AndetAreal
                    byg049ArealAfOverdaekketAreal
                    byg050ArealAabneOverdaekningerPaaBygningenSamlet
                    byg051Adgangsareal
                    byg052BeregningsprincipCarportAreal
                    byg053BygningsarealerKilde
                    byg054AntalEtager
                    byg055AfvigendeEtager
                    byg056Varmeinstallation
                    byg057Opvarmningsmiddel
                    byg058SupplerendeVarme
                    byg069Sikringsrumpladser
                    byg070Fredning
                    byg071BevaringsvaerdighedReference
                    byg094Revisionsdato
                    byg111StormraadetsOversvoemmelsesSelvrisiko
                    byg112DatoForRegistreringFraStormraadet
                    byg113Byggeskadeforsikringsselskab
                    byg114DatoForByggeskadeforsikring
                    byg119Udledningstilladelse
                    byg121OmfattetAfByggeskadeforsikring
                    byg122Gyldighedsdato
                    byg123MedlemskabAfSpildevandsforsyning
                    byg124PaabudVedrSpildevandsafledning
                    byg125FristVedrSpildevandsafledning
                    byg126TilladelseTilUdtraeden
                    byg127DatoForTilladelseTilUdtraeden
                    byg128TilladelseTilAlternativBortskaffelseEllerAfledning
                    byg129DatoForTilladelseTilAlternativBortskaffelseEllerAfledning
                    byg130ArealAfUdvendigEfterisolering
                    byg131DispensationFritagelseIftKollektivVarmeforsyning
                    byg132DatoForDispensationFritagelseIftKollektivVarmeforsyning
                    byg133KildeTilKoordinatsaet
                    byg134KvalitetAfKoordinatsaet
                    byg135SupplerendeOplysningOmKoordinatsaet
                    byg136PlaceringPaaSoeterritorie
                    byg137BanedanmarkBygvaerksnummer
                    byg140ServitutForUdlejningsEjendomDato
                    byg150Gulvbelaegning
                    byg151Frihoejde
                    byg152AabenLukketKonstruktion
                    byg153Konstruktionsforhold
                    byg301TypeAfFlytning
                    byg302Tilflytterkommune
                    byg403OevrigeBemaerkningerFraStormraadet
                    byg404Koordinat {
                        wkt
                        crs
                    }
                    byg406Koordinatsystem
                    byg500Notatlinjer
                    datafordelerOpdateringstid
                    datafordelerRegisterImportSequenceNumber
                    datafordelerRowId
                    datafordelerRowVersion
                    ejerlejlighed
                    forretningshaendelse
                    forretningsomraade
                    forretningsproces
                    grund
                    husnummer
                    id_lokalId
                    id_namespace
                    jordstykke
                    kommunekode
                    registreringFra
                    registreringsaktoer
                    registreringTil
                    status
                    virkningFra
                    virkningsaktoer
                    virkningTil
                }
                registreringFra
                registreringsaktoer
                registreringsspecifikation
                registreringTil
                status
                synligBygning
                tempID
                underMinimumBygning
                vertikalNoejagtighed
                vertikalStedfaestelsesmetode
                virkningFra
                virkningsaktoer
                virkningTil
                }
            }
        }
    -> StringReplacer_29
StringReplacer_29
    CASE = NO
    FIND_TEXT = <pageInfo.endCursor>
    NO_MATCH = _FME_NO_OP_
    REGEXP = NO
    REPLACE_TEXT = @Value(_v_cursor)
    SRC_ATTRS = _gql
    -> GraphQLtoJSON_2
GraphQLtoJSON_2
    GQL = @Value(_gql)
    -> AttributeRemover_3
AttributeRemover_3
    LIST_ATTRS = nodes{}
    -> HTTPCaller_2

Bookmark: 5. Consecutive calls with different cursors. Secret sauce variable-handling.
HTTPCaller_2
    AUTH_METHOD_TYPE = NC
    AUTH_NAMED_CONNECTION = DAF GraphQL API Key v1
    CLIENT_CERTIFICATE_TYPE = NONE
    CONNECTION_TIMEOUT_LENGTH = 60
    CONTENT_TYPE_LOOKUP = application/json
    ERROR_ATTR = _error
    FOLLOW_REDIRECTS = FOLLOW_WITH_GET
    HTTP_METHOD = POST
    MAX_HTTP_VERSION = HTTP_2
    MAX_TRANSFERS_IN_PROGRESS = 1
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://graphql.datafordeler.dk/flexible/v1/
    TRANSFER_TIMEOUT_LENGTH = 90
    UPLOAD_BODY = @Value(_gql_rest)
    UPLOAD_TYPE = STRING_UPLOAD
    USE_COOKIES = No
    VERIFY_SSL_CERTIFICATES = Yes
    AUTH_METHOD = Web Connection
    UPLOAD_CONTENT_TYPE = JSON (application/json)
    -> JSONFragmenter_2
    <REJECTED> -> Junction_4
JSONFragmenter_2
    EXPLODE_FORMAT = JSON
    EXTRACT_ATTR = Yes
    JSON_ATTR = _response_body
    JSON_QUERY = json[*][*]
    NEW_ATTRIBUTES = nodes{} buffer pageInfo.endCursor buffer pageInfo.hasNextPage buffer
    READ_FROM_FILE = NO
    RECURSIVE = YES
    REJECT_EMPTY_LISTS = YES
    FRAGMENTS -> Tester_8
    <REJECTED> -> Junction_6
Tester_8
    BOOL_OP = OR
    TEST_CLAUSE = TEST @Value(pageInfo.hasNextPage) = Yes
    TEST_MODE = TEST
    PASSED -> VariableSetter_2
    FAILED -> VariableSetter_3
VariableSetter_2
    SCOPE = Global
    VALUE = @Value(pageInfo.endCursor)
    VARNAME = vEndCursor
    -> Junction_11
VariableSetter_3
    SCOPE = Global
    VALUE = lastpage
    VARNAME = vEndCursor
    -> Junction_11
Note: To: error logging
Junction_6
    -> Junction_7
Note: AttributeCreator_11 : to error logging
Junction_4
    -> Junction_5

Bookmark: 6. Get all records in all nodes-lists
JSONFragmenter_5
    EXPLODE_FORMAT = JSON
    EXTRACT_ATTR = Yes
    JSON_ATTR = _response_body
    JSON_QUERY = json["nodes"][*]
    NEW_ATTRIBUTES = id_lokalId buffer
    READ_FROM_FILE = NO
    RECURSIVE = YES
    REJECT_EMPTY_LISTS = YES
    FRAGMENTS -> AttributeRemover
    <REJECTED> -> Junction_2
AttributeRemover
    LIST_ATTRS = nodes{}
    -> AttributeExposer_3
AttributeExposer_3
    ATTR_TABLE = applikation,varchar(50),BBRaktion,varchar(17),BBRUUID,varchar(36),bygningstype,varchar(9),dataansvar,varchar(12),datafordelerOpdateringstid,varchar(27),datafordelerRegisterImportSequenceNumber,uint32,datafordelerRowId,varchar(36),datafordelerRowVersion,uint8,feltliste,varchar(200),forretningshaendelse,varchar(28),forretningsomraade,uint8,forretningsproces,varchar(28),geometri.crs,uint16,geometri.wkt,varchar(1475),geometristatus,varchar(10),id_lokalId,uint32,id_namespace,varchar(29),kommentar,varchar(25),maalestedBygning,varchar(12),metode3D,varchar(12),objectid,real64,overlapBygning,varchar(2),planNoejagtighed,real32,planStedfaestelsesmetode,varchar(13),referererTil,varchar(200),referererTil.byg007Bygningsnummer,uint8,referererTil.byg021BygningensAnvendelse,uint16,referererTil.byg024AntalLejlighederMedKoekken,varchar(200),referererTil.byg025AntalLejlighederUdenKoekken,varchar(200),referererTil.byg026Opfoerelsesaar,uint16,referererTil.byg027OmTilbygningsaar,uint16,referererTil.byg029DatoForMidlertidigOpfoertBygning,varchar(27),referererTil.byg030Vandforsyning,uint8,referererTil.byg031Afloebsforhold,uint8,referererTil.byg032YdervaeggensMateriale,uint8,referererTil.byg033Tagdaekningsmateriale,uint8,referererTil.byg034SupplerendeYdervaeggensMateriale,varchar(200),referererTil.byg035SupplerendeTagdaekningsMateriale,varchar(200),referererTil.byg036AsbestholdigtMateriale,varchar(200),referererTil.byg037KildeTilBygningensMaterialer,uint8,referererTil.byg038SamletBygningsareal,uint16,referererTil.byg039BygningensSamledeBoligAreal,uint16,referererTil.byg040BygningensSamledeErhvervsAreal,uint16,referererTil.byg041BebyggetAreal,uint16,referererTil.byg042ArealIndbyggetGarage,varchar(200),referererTil.byg043ArealIndbyggetCarport,varchar(200),referererTil.byg044ArealIndbyggetUdhus,uint8,referererTil.byg045ArealIndbyggetUdestueEllerLign,uint8,referererTil.byg046SamletArealAfLukkedeOverdaekningerPaaBygningen,varchar(200),referererTil.byg047ArealAfAffaldsrumITerraenniveau,varchar(200),referererTil.byg048AndetAreal,uint8,referererTil.byg049ArealAfOverdaekketAreal,uint8,referererTil.byg050ArealAabneOverdaekningerPaaBygningenSamlet,varchar(200),referererTil.byg051Adgangsareal,uint8,referererTil.byg052BeregningsprincipCarportAreal,varchar(200),referererTil.byg053BygningsarealerKilde,uint8,referererTil.byg054AntalEtager,uint8,referererTil.byg055AfvigendeEtager,uint8,referererTil.byg056Varmeinstallation,uint8,referererTil.byg057Opvarmningsmiddel,uint8,referererTil.byg058SupplerendeVarme,uint8,referererTil.byg069Sikringsrumpladser,uint16,referererTil.byg070Fredning,uint8,referererTil.byg071BevaringsvaerdighedReference,varchar(200),referererTil.byg094Revisionsdato,varchar(27),referererTil.byg111StormraadetsOversvoemmelsesSelvrisiko,varchar(200),referererTil.byg112DatoForRegistreringFraStormraadet,varchar(200),referererTil.byg113Byggeskadeforsikringsselskab,uint8,referererTil.byg114DatoForByggeskadeforsikring,varchar(27),referererTil.byg119Udledningstilladelse,varchar(200),referererTil.byg121OmfattetAfByggeskadeforsikring,uint8,referererTil.byg122Gyldighedsdato,varchar(27),referererTil.byg123MedlemskabAfSpildevandsforsyning,varchar(200),referererTil.byg124PaabudVedrSpildevandsafledning,varchar(200),referererTil.byg125FristVedrSpildevandsafledning,varchar(200),referererTil.byg126TilladelseTilUdtraeden,varchar(200),referererTil.byg127DatoForTilladelseTilUdtraeden,varchar(200),referererTil.byg128TilladelseTilAlternativBortskaffelseEllerAfledning,varchar(200),referererTil.byg129DatoForTilladelseTilAlternativBortskaffelseEllerAfledning,varchar(200),referererTil.byg130ArealAfUdvendigEfterisolering,varchar(200),referererTil.byg131DispensationFritagelseIftKollektivVarmeforsyning,varchar(200),referererTil.byg132DatoForDispensationFritagelseIftKollektivVarmeforsyning,varchar(200),referererTil.byg133KildeTilKoordinatsaet,varchar(1),referererTil.byg134KvalitetAfKoordinatsaet,uint8,referererTil.byg135SupplerendeOplysningOmKoordinatsaet,uint8,referererTil.byg136PlaceringPaaSoeterritorie,uint8,referererTil.byg137BanedanmarkBygvaerksnummer,varchar(200),referererTil.byg140ServitutForUdlejningsEjendomDato,varchar(200),referererTil.byg150Gulvbelaegning,varchar(200),referererTil.byg151Frihoejde,varchar(200),referererTil.byg152AabenLukketKonstruktion,varchar(200),referererTil.byg153Konstruktionsforhold,varchar(200),referererTil.byg301TypeAfFlytning,varchar(200),referererTil.byg302Tilflytterkommune,varchar(200),referererTil.byg403OevrigeBemaerkningerFraStormraadet,varchar(200),referererTil.byg404Koordinat.crs,uint16,referererTil.byg404Koordinat.wkt,varchar(28),referererTil.byg406Koordinatsystem,uint8,referererTil.byg500Notatlinjer,varchar(200),referererTil.bygningEjerlejlighed,varchar(200),referererTil.bygningEjerlejlighed.ejendommensEjerforholdskode,uint8,referererTil.bygningEjerlejlighed.ejendomsnummer,uint32,referererTil.bygningEjerlejlighed.ejendomstype,uint8,referererTil.bygningEjerlejlighed.ejerlejlighed,uint32,referererTil.bygningEjerlejlighed.ejerlejlighedsnummer,uint8,referererTil.bygningEjerlejlighed.id_lokalId,varchar(36),referererTil.bygningEjerlejlighed.id_namespace,varchar(39),referererTil.bygningEjerlejlighed.kommunekode,uint16,referererTil.bygningEjerlejlighed.registreringFra,varchar(27),referererTil.bygningEjerlejlighed.registreringsaktoer,varchar(3),referererTil.bygningEjerlejlighed.registreringTil,varchar(200),referererTil.bygningEjerlejlighed.samletFastEjendom,varchar(200),referererTil.bygningEjerlejlighed.status,uint8,referererTil.bygningEjerlejlighed.tinglystAreal,uint8,referererTil.bygningEjerlejlighed.virkningFra,varchar(27),referererTil.bygningEjerlejlighed.virkningsaktoer,varchar(3),referererTil.bygningEjerlejlighed.virkningTil,varchar(200),referererTil.bygningEjerlejlighed.vurderingsejendomsnummer,varchar(200),referererTil.bygningGrund.bestemtFastEjendom,varchar(36),referererTil.bygningGrund.datafordelerOpdateringstid,varchar(27),referererTil.bygningGrund.datafordelerRegisterImportSequenceNumber,uint32,referererTil.bygningGrund.datafordelerRowId,varchar(36),referererTil.bygningGrund.datafordelerRowVersion,uint8,referererTil.bygningGrund.forretningshaendelse,varchar(5),referererTil.bygningGrund.forretningsomraade,varchar(11),referererTil.bygningGrund.forretningsproces,uint8,referererTil.bygningGrund.gru009Vandforsyning,uint8,referererTil.bygningGrund.gru010Afloebsforhold,uint8,referererTil.bygningGrund.gru021Udledningstilladelse,varchar(200),referererTil.bygningGrund.gru022MedlemskabAfSpildevandsforsyning,varchar(200),referererTil.bygningGrund.gru023PaabudVedrSpildevandsafledning,uint8,referererTil.bygningGrund.gru024FristVedrSpildevandsafledning,varchar(27),referererTil.bygningGrund.gru025TilladelseTilUdtraeden,varchar(200),referererTil.bygningGrund.gru026DatoForTilladelseTilUdtraeden,varchar(200),referererTil.bygningGrund.gru027TilladelseTilAlternativBortskaffelseEllerAfledning,varchar(200),referererTil.bygningGrund.gru028DatoForTilladelseTilAlternativBortskaffelseEllerAfledning,varchar(200),referererTil.bygningGrund.gru029DispensationFritagelseIftKollektivVarmeforsyning,varchar(200),referererTil.bygningGrund.gru030DatoForDispensationFritagelseIftKollektivVarmeforsyning,varchar(200),referererTil.bygningGrund.gru500Notatlinjer,varchar(200),referererTil.bygningGrund.husnummer,varchar(36),referererTil.bygningGrund.id_lokalId,varchar(36),referererTil.bygningGrund.id_namespace,varchar(28),referererTil.bygningGrund.kommunekode,uint16,referererTil.bygningGrund.registreringFra,varchar(27),referererTil.bygningGrund.registreringsaktoer,varchar(3),referererTil.bygningGrund.registreringTil,varchar(200),referererTil.bygningGrund.status,uint8,referererTil.bygningGrund.virkningFra,varchar(27),referererTil.bygningGrund.virkningsaktoer,varchar(16),referererTil.bygningGrund.virkningTil,varchar(200),referererTil.datafordelerOpdateringstid,varchar(27),referererTil.datafordelerRegisterImportSequenceNumber,uint32,referererTil.datafordelerRowId,varchar(36),referererTil.datafordelerRowVersion,uint8,referererTil.ejerlejlighed,varchar(36),referererTil.forretningshaendelse,varchar(7),referererTil.forretningsomraade,varchar(11),referererTil.forretningsproces,uint8,referererTil.grund,varchar(36),referererTil.husnummer,varchar(36),referererTil.husnummerBygning.adgangsadressebetegnelse,varchar(39),referererTil.husnummerBygning.adgangspunkt,varchar(36),referererTil.husnummerBygning.adgangTilBygning,varchar(36),referererTil.husnummerBygning.adgangTilTekniskAnlaeg,varchar(200),referererTil.husnummerBygning.afstemningsomraade,uint32,referererTil.husnummerBygning.datafordelerOpdateringstid,varchar(27),referererTil.husnummerBygning.datafordelerRegisterImportSequenceNumber,uint32,referererTil.husnummerBygning.datafordelerRowId,varchar(36),referererTil.husnummerBygning.datafordelerRowVersion,uint8,referererTil.husnummerBygning.forretningshaendelse,uint8,referererTil.husnummerBygning.forretningsomraade,varchar(11),referererTil.husnummerBygning.forretningsproces,uint8,referererTil.husnummerBygning.geoDanmarkBygning,uint32,referererTil.husnummerBygning.husnummerretning.crs,uint16,referererTil.husnummerBygning.husnummerretning.wkt,varchar(45),referererTil.husnummerBygning.husnummertekst,varchar(3),referererTil.husnummerBygning.id_lokalId,varchar(36),referererTil.husnummerBygning.id_namespace,varchar(32),referererTil.husnummerBygning.jordstykke,uint32,referererTil.husnummerBygning.kommuneinddeling,uint32,referererTil.husnummerBygning.menighedsraadsafstemningsomraade,uint32,referererTil.husnummerBygning.navngivenVej,varchar(36),referererTil.husnummerBygning.placeretPaaForeloebigtJordstykke,varchar(200),referererTil.husnummerBygning.postnummer,varchar(36),referererTil.husnummerBygning.registreringFra,varchar(27),referererTil.husnummerBygning.registreringsaktoer,varchar(3),referererTil.husnummerBygning.registreringTil,varchar(200),referererTil.husnummerBygning.sogneinddeling,uint32,referererTil.husnummerBygning.status,uint8,referererTil.husnummerBygning.supplerendeBynavn,varchar(200),referererTil.husnummerBygning.vejmidte,varchar(9),referererTil.husnummerBygning.vejpunkt,varchar(36),referererTil.husnummerBygning.virkningFra,varchar(27),referererTil.husnummerBygning.virkningsaktoer,varchar(39),referererTil.husnummerBygning.virkningTil,varchar(200),referererTil.id_lokalId,varchar(36),referererTil.id_namespace,varchar(30),referererTil.jordstykke,uint32,referererTil.kommunekode,uint16,referererTil.registreringFra,varchar(27),referererTil.registreringsaktoer,varchar(3),referererTil.registreringTil,varchar(200),referererTil.status,uint8,referererTil.virkningFra,varchar(27),referererTil.virkningsaktoer,varchar(16),referererTil.virkningTil,varchar(200),registreringFra,varchar(27),registreringsaktoer,varchar(31),registreringsspecifikation,varchar(19),registreringTil,varchar(200),status,varchar(18),synligBygning,varchar(3),tempID,varchar(200),underMinimumBygning,varchar(3),vertikalNoejagtighed,real32,vertikalStedfaestelsesmetode,varchar(13),virkningFra,varchar(27),virkningsaktoer,varchar(31),virkningTil,varchar(200)
    -> AttributeKeeper_2
AttributeKeeper_2
    CREATE_BULK_MODE_FEATURES = NO
    KEEP_ATTRS = id_lokalId,id_namespace,datafordelerOpdateringstid,geometri.crs,geometri.wkt,BBRUUID,BBRaktion,applikation,bygningstype,dataansvar,feltliste,referererTil.byg007Bygningsnummer,referererTil.byg021BygningensAnvendelse,referererTil.byg024AntalLejlighederMedKoekken,referererTil.byg025AntalLejlighederUdenKoekken,referererTil.byg026Opfoerelsesaar,referererTil.id_lokalId,datafordelerRegisterImportSequenceNumber,datafordelerRowId,datafordelerRowVersion,forretningshaendelse,forretningsomraade,forretningsproces,geometristatus,kommentar,maalestedBygning,metode3D,objectid,overlapBygning,planNoejagtighed,planStedfaestelsesmetode,referererTil,referererTil.byg027OmTilbygningsaar,referererTil.byg029DatoForMidlertidigOpfoertBygning,referererTil.byg030Vandforsyning,referererTil.byg031Afloebsforhold,referererTil.byg032YdervaeggensMateriale,referererTil.byg033Tagdaekningsmateriale,referererTil.byg034SupplerendeYdervaeggensMateriale,referererTil.byg035SupplerendeTagdaekningsMateriale,referererTil.byg036AsbestholdigtMateriale,referererTil.byg037KildeTilBygningensMaterialer,referererTil.byg038SamletBygningsareal,referererTil.byg039BygningensSamledeBoligAreal,referererTil.byg040BygningensSamledeErhvervsAreal,referererTil.byg041BebyggetAreal,referererTil.byg042ArealIndbyggetGarage,referererTil.byg043ArealIndbyggetCarport,referererTil.byg044ArealIndbyggetUdhus,referererTil.byg045ArealIndbyggetUdestueEllerLign,referererTil.byg046SamletArealAfLukkedeOverdaekningerPaaBygningen,referererTil.byg047ArealAfAffaldsrumITerraenniveau,referererTil.byg048AndetAreal,referererTil.byg049ArealAfOverdaekketAreal,referererTil.byg050ArealAabneOverdaekningerPaaBygningenSamlet,referererTil.byg051Adgangsareal,referererTil.byg052BeregningsprincipCarportAreal,referererTil.byg053BygningsarealerKilde,referererTil.byg054AntalEtager,referererTil.byg055AfvigendeEtager,referererTil.byg056Varmeinstallation,referererTil.byg057Opvarmningsmiddel,referererTil.byg058SupplerendeVarme,referererTil.byg069Sikringsrumpladser,referererTil.byg070Fredning,referererTil.byg071BevaringsvaerdighedReference,referererTil.byg094Revisionsdato,referererTil.byg111StormraadetsOversvoemmelsesSelvrisiko,referererTil.byg112DatoForRegistreringFraStormraadet,referererTil.byg113Byggeskadeforsikringsselskab,referererTil.byg114DatoForByggeskadeforsikring,referererTil.byg119Udledningstilladelse,referererTil.byg121OmfattetAfByggeskadeforsikring,referererTil.byg122Gyldighedsdato,referererTil.byg123MedlemskabAfSpildevandsforsyning,referererTil.byg124PaabudVedrSpildevandsafledning,referererTil.byg125FristVedrSpildevandsafledning,referererTil.byg126TilladelseTilUdtraeden,referererTil.byg127DatoForTilladelseTilUdtraeden,referererTil.byg128TilladelseTilAlternativBortskaffelseEllerAfledning,referererTil.byg129DatoForTilladelseTilAlternativBortskaffelseEllerAfledning,referererTil.byg130ArealAfUdvendigEfterisolering,referererTil.byg131DispensationFritagelseIftKollektivVarmeforsyning,referererTil.byg132DatoForDispensationFritagelseIftKollektivVarmeforsyning,referererTil.byg133KildeTilKoordinatsaet,referererTil.byg134KvalitetAfKoordinatsaet,referererTil.byg135SupplerendeOplysningOmKoordinatsaet,referererTil.byg136PlaceringPaaSoeterritorie,referererTil.byg137BanedanmarkBygvaerksnummer,referererTil.byg140ServitutForUdlejningsEjendomDato,referererTil.byg150Gulvbelaegning,referererTil.byg151Frihoejde,referererTil.byg152AabenLukketKonstruktion,referererTil.byg153Konstruktionsforhold,referererTil.byg301TypeAfFlytning,referererTil.byg302Tilflytterkommune,referererTil.byg403OevrigeBemaerkningerFraStormraadet,referererTil.byg404Koordinat.crs,referererTil.byg404Koordinat.wkt,referererTil.byg406Koordinatsystem,referererTil.byg500Notatlinjer,referererTil.bygningEjerlejlighed,referererTil.bygningEjerlejlighed.ejendommensEjerforholdskode,referererTil.bygningEjerlejlighed.ejendomsnummer,referererTil.bygningEjerlejlighed.ejendomstype,referererTil.bygningEjerlejlighed.ejerlejlighed,referererTil.bygningEjerlejlighed.ejerlejlighedsnummer,referererTil.bygningEjerlejlighed.id_lokalId,referererTil.bygningEjerlejlighed.id_namespace,referererTil.bygningEjerlejlighed.kommunekode,referererTil.bygningEjerlejlighed.registreringFra,referererTil.bygningEjerlejlighed.registreringTil,referererTil.bygningEjerlejlighed.registreringsaktoer,referererTil.bygningEjerlejlighed.samletFastEjendom,referererTil.bygningEjerlejlighed.status,referererTil.bygningEjerlejlighed.tinglystAreal,referererTil.bygningEjerlejlighed.virkningFra,referererTil.bygningEjerlejlighed.virkningTil,referererTil.bygningEjerlejlighed.virkningsaktoer,referererTil.bygningEjerlejlighed.vurderingsejendomsnummer,referererTil.bygningGrund.bestemtFastEjendom,referererTil.bygningGrund.datafordelerOpdateringstid,referererTil.bygningGrund.datafordelerRegisterImportSequenceNumber,referererTil.bygningGrund.datafordelerRowId,referererTil.bygningGrund.datafordelerRowVersion,referererTil.bygningGrund.forretningshaendelse,referererTil.bygningGrund.forretningsomraade,referererTil.bygningGrund.forretningsproces,referererTil.bygningGrund.gru009Vandforsyning,referererTil.bygningGrund.gru010Afloebsforhold,referererTil.bygningGrund.gru021Udledningstilladelse,referererTil.bygningGrund.gru022MedlemskabAfSpildevandsforsyning,referererTil.bygningGrund.gru023PaabudVedrSpildevandsafledning,referererTil.bygningGrund.gru024FristVedrSpildevandsafledning,referererTil.bygningGrund.gru025TilladelseTilUdtraeden,referererTil.bygningGrund.gru026DatoForTilladelseTilUdtraeden,referererTil.bygningGrund.gru027TilladelseTilAlternativBortskaffelseEllerAfledning,referererTil.bygningGrund.gru028DatoForTilladelseTilAlternativBortskaffelseEllerAfledning,referererTil.bygningGrund.gru029DispensationFritagelseIftKollektivVarmeforsyning,referererTil.bygningGrund.gru030DatoForDispensationFritagelseIftKollektivVarmeforsyning,referererTil.bygningGrund.gru500Notatlinjer,referererTil.bygningGrund.husnummer,referererTil.bygningGrund.id_lokalId,referererTil.bygningGrund.id_namespace,referererTil.bygningGrund.kommunekode,referererTil.bygningGrund.registreringFra,referererTil.bygningGrund.registreringTil,referererTil.bygningGrund.registreringsaktoer,referererTil.bygningGrund.status,referererTil.bygningGrund.virkningFra,referererTil.bygningGrund.virkningTil,referererTil.bygningGrund.virkningsaktoer,referererTil.datafordelerOpdateringstid,referererTil.datafordelerRegisterImportSequenceNumber,referererTil.datafordelerRowId,referererTil.datafordelerRowVersion,referererTil.ejerlejlighed,referererTil.forretningshaendelse,referererTil.forretningsomraade,referererTil.forretningsproces,referererTil.grund,referererTil.husnummer,referererTil.husnummerBygning.adgangTilBygning,referererTil.husnummerBygning.adgangTilTekniskAnlaeg,referererTil.husnummerBygning.adgangsadressebetegnelse,referererTil.husnummerBygning.adgangspunkt,referererTil.husnummerBygning.afstemningsomraade,referererTil.husnummerBygning.datafordelerOpdateringstid,referererTil.husnummerBygning.datafordelerRegisterImportSequenceNumber,referererTil.husnummerBygning.datafordelerRowId,referererTil.husnummerBygning.datafordelerRowVersion,referererTil.husnummerBygning.forretningshaendelse,referererTil.husnummerBygning.forretningsomraade,referererTil.husnummerBygning.forretningsproces,referererTil.husnummerBygning.geoDanmarkBygning,referererTil.husnummerBygning.husnummerretning.crs,referererTil.husnummerBygning.husnummerretning.wkt,referererTil.husnummerBygning.husnummertekst,referererTil.husnummerBygning.id_lokalId,referererTil.husnummerBygning.id_namespace,referererTil.husnummerBygning.jordstykke,referererTil.husnummerBygning.kommuneinddeling,referererTil.husnummerBygning.menighedsraadsafstemningsomraade,referererTil.husnummerBygning.navngivenVej,referererTil.husnummerBygning.placeretPaaForeloebigtJordstykke,referererTil.husnummerBygning.postnummer,referererTil.husnummerBygning.registreringFra,referererTil.husnummerBygning.registreringTil,referererTil.husnummerBygning.registreringsaktoer,referererTil.husnummerBygning.sogneinddeling,referererTil.husnummerBygning.status,referererTil.husnummerBygning.supplerendeBynavn,referererTil.husnummerBygning.vejmidte,referererTil.husnummerBygning.vejpunkt,referererTil.husnummerBygning.virkningFra,referererTil.husnummerBygning.virkningTil,referererTil.husnummerBygning.virkningsaktoer,referererTil.id_namespace,referererTil.jordstykke,referererTil.kommunekode,referererTil.registreringFra,referererTil.registreringTil,referererTil.registreringsaktoer,referererTil.status,referererTil.virkningFra,referererTil.virkningTil,referererTil.virkningsaktoer,registreringFra,registreringTil,registreringsaktoer,registreringsspecifikation,status,synligBygning,tempID,underMinimumBygning,vertikalNoejagtighed,vertikalStedfaestelsesmetode,virkningFra,virkningTil,virkningsaktoer
    -> AttributeCreator_14
AttributeCreator_14
    ATTR_TABLE = SET_TO _crs_ogc (varchar(200)) = urn:ogc:def:crs:EPSG::@Value(geometri.crs)
    -> GeometryReplacer
    -> AttributeCreator_18
GeometryReplacer
    KIND = wkt
    OGC_WKT_PRECISION = FLOAT_64
    REMOVE_ATTRIBUTE = No
    SOURCE = @Value(geometri.wkt)
    KIND_LONG = OGC Well Known Text
    OGC_WKT_PRECISION_DISPLAY = 64-bit
    -> GeometryExtractor
GeometryExtractor
    ATTR = _geometry
    JSON_MAX_DIGITS = 7
    KIND = GEOJSON
    REMOVE_GEOMETRY = No
    KIND_LONG = GeoJSON
    -> JSONTemplater_2 [SUB]
Creator_2
    GEOMTYPE = Geometry Object
    NUM = 1
    CREATED -> JSONTemplater_2 [ROOT]
JSONTemplater_2
    RESULT_ATTRIBUTE = response.body.content
    ROOT_QUERY_EXPR:
      {
         "type": "FeatureCollection",
         "features": [
          fme:process-features("SUB")
         ]
      }
    SUB_QUERY_EXPR:
      {
              "type": "Feature",
              "geometry": {
                  fme:get-attribute("_geometry")
              },
              "properties": {
                  "id_lokalId": fme:get-attribute("id_lokalId"),
                  "id_namespace": fme:get-attribute("id_namespace"),
                  "byg404Koordinat":
                      {
                          "crs": fme:get-attribute("referererTil.byg404Koordinat.crs"),
                          "wkt": fme:get-attribute("referererTil.byg404Koordinat.wkt")
                      },
                  "forretningshændelse": fme:get-attribute("forretningshaendelse"),
                  "forretningsområde": fme:get-attribute("forretningsomraade"),
                  "forretningsproces": fme:get-attribute("forretningsproces"),
                  "husnummer": {
                      "adgangTilBygning": fme:get-attribute("referererTil.husnummerBygning.adgangTilBygning"),
                      "adgangsadressebetegnelse": fme:get-attribute("referererTil.husnummerBygning.adgangsadressebetegnelse"),
                      "adgangspunkt": fme:get-attribute("referererTil.husnummerBygning.adgangspunkt"),
                      "husnummertekst": fme:get-attribute("referererTil.husnummerBygning.husnummertekst"),
                      "id_lokalId": fme:get-attribute("referererTil.husnummerBygning.id_lokalId"),
                      "id_namespace": fme:get-attribute("referererTil.husnummerBygning.id_namespace"),
                      "jordstykke": fme:get-attribute("referererTil.husnummerBygning.jordstykke"),
                      "kommuneinddeling": fme:get-attribute("referererTil.husnummerBygning.kommuneinddeling"),
                      "menighedsraadsafstemningsomraade": fme:get-attribute("referererTil.husnummerBygning.menighedsraadsafstemningsomraade"),
                      "navngivenVej": fme:get-attribute("referererTil.husnummerBygning.navngivenVej"),
                      "placeretPaaForeloebigtJordstykke": fme:get-attribute("referererTil.husnummerBygning.placeretPaaForeloebigtJordstykke"),
                      "postnummer": fme:get-attribute("referererTil.husnummerBygning.postnummer"),
                      "registreringFra": fme:get-attribute("referererTil.husnummerBygning.registreringFra"),
                      "status": fme:get-attribute("referererTil.husnummerBygning.status"),
                      "vejmidte": fme:get-attribute("referererTil.husnummerBygning.vejmidte"),
                      "vejpunkt": fme:get-attribute("referererTil.husnummerBygning.vejpunkt"),
                      "virkningFra": fme:get-attribute("referererTil.husnummerBygning.virkningFra")
                  },
                  "registreringFra": fme:get-attribute("registreringFra"),
                  "status": fme:get-attribute("status"),
                  "virkningFra": fme:get-attribute("virkningFra")
              }
      }
    VISIBLE_QUERY_VALIDATE = Yes
    -> AttributeCreator_10

Bookmark: Save to DB (Spatialite)
AttributeCreator_18
    ATTR_TABLE = SET_TO _coordsys (varchar(200)) = EPSG:@Value(geometri.crs)
    -> CoordinateSystemSetter_2
CoordinateSystemSetter_2
    COORDSYS = @Value(_coordsys)
    -> GeometryReplacer_3
GeometryReplacer_3
    KIND = wkt
    OGC_WKT_PRECISION = FLOAT_64
    REMOVE_ATTRIBUTE = Yes
    SOURCE = @Value(geometri.wkt)
    KIND_LONG = OGC Well Known Text
    OGC_WKT_PRECISION_DISPLAY = 64-bit
    -> AttributeCreator_24
    <REJECTED> -> Logger_2
AttributeCreator_24
    ATTR_TABLE:
      SET_TO _foreignKey (varchar(200)) = @UUID()
      SET_TO adgangsadressebetegnelse (varchar(200)) = @Value(referererTil.husnummerBygning.adgangsadressebetegnelse)
    -> FeatureWriter [Output]
Note: Write to Spatialite DB: / - Bygning_info: GEODKV_Bygning + BBR_Bygning + DAR_Husnummer + DAR_Adressepunkt with genometry representing adgangsadresse / - Adresser: all address points contained within each adgangsadresse
FeatureWriter
    CONFIG_PARAMETERS = ESCAPE_COMMAS_IN_FTP_FORMAT_PARAMETERS,no
    DATASET = $(FME_MF_DIR_USERTYPED)\Datafordeleren_demodata.sqlite
    DATASET_ATTR = _dataset
    FEATURE_TYPE_LIST_ATTR = _feature_types
    FORMAT = SPATIALITE_NATIVE
    SPATIALITE_NATIVE_ALWAYS_CREATE_FEATURE_TYPES = NO
    SPATIALITE_NATIVE_COMPRESS_GEOMETRY = NO
    SPATIALITE_NATIVE_COORDINATE_SYSTEM_GRANULARITY = FEATURE_TYPE
    SPATIALITE_NATIVE_CREATE_SPATIAL_INDEX = YES
    SPATIALITE_NATIVE_DESTINATION_DATASETTYPE_VALIDATION = Yes
    SPATIALITE_NATIVE_DIMENSION = AUTO
    SPATIALITE_NATIVE_ENCODING = utf-8
    SPATIALITE_NATIVE_OVERWRITE_FILE = No
    SPATIALITE_NATIVE_SUPPORT_INTERNATIONALIZATION = YES
    SPATIALITE_NATIVE_TRANSACTION_INTERVAL = 500
    SPATIALITE_NATIVE_WRITER_MODE = INSERT
    TOTAL_FEATURES_WRITTEN_ATTR = _total_features_written
Logger_2
    LOG_FEATURE = LOG_ONLY
    MAXCOORDS = 20
    MAXFEATS = 20
    MESSAGE = Feature is:
    SEVERITY = INFO

Bookmark: Error logging /logging
AttributeCreator_13
    ATTR_TABLE:
      SET_TO response.body.content_type (varchar(16)) = application/json
      SET_TO response.status_code (uint16) = 500; @Value(fme_rejection_code)
      SET_TO response.body.content (varchar(200)) = @Value(_response_body)
    -> Logger
AttributeCreator_11
    ATTR_TABLE:
      SET_TO response.body.content_type (varchar(16)) = application/json
      SET_TO response.status_code (uint16) = 500
      SET_TO response.body.content (varchar(200)) = @Value(_response_body)
    -> Logger
AttributeCreator_10
    ATTR_TABLE:
      SET_TO response.body.content_type (varchar(16)) = application/json
      SET_TO response.status_code (uint8) = 200
    -> Logger
Logger
    LOG_FEATURE = LOG_ONLY
    MAXCOORDS = 20
    MAXFEATS = 20
    MESSAGE = Feature is:
    SEVERITY = INFO

Bookmark: New Bookmark
Note: Query som virker
AttributeCreator_5
    ATTR_TABLE:
      SET_TO _gql (varchar(200)) = query {
            GEODKV_Bygning(
                virkningstid: "@Value(query.VirkningFra)",
                registreringstid: "@Value(query.RegistreringFra)"
                first: 200
                where: {
                    geometri: {
                        within: {
                            crs: 25832
                            wkt: "MULTIPOLYGON(((@Value(query.xmin) @Value(query.ymin), @Value(query.xmin) @Value(query.ymax), @Value(query.xmax) @Value(query.ymax), @Value(query.xmax) @Value(query.ymin), @Value(query.xmin) @Value(query.ymin))))"
                        }
                    }
                }
            ) {
            pageInfo {
              endCursor
              hasNextPage
            }
            nodes
                {
                applikation
                BBRaktion
                BBRUUID
                bygningstype
                dataansvar
                datafordelerOpdateringstid
                datafordelerRegisterImportSequenceNumber
                datafordelerRowId
                datafordelerRowVersion
                feltliste
                forretningshaendelse
                forretningsomraade
                forretningsproces
                geometri {
                    wkt
                    crs
                }
                geometristatus
                id_lokalId
                id_namespace
                kommentar
                maalestedBygning
                metode3D
                objectid
                overlapBygning
                planNoejagtighed
                planStedfaestelsesmetode
                registreringFra
                registreringsaktoer
                registreringsspecifikation
                registreringTil
                status
                synligBygning
                tempID
                underMinimumBygning
                vertikalNoejagtighed
                vertikalStedfaestelsesmetode
                virkningFra
                virkningsaktoer
                virkningTil
                referererTil {
                    datafordelerOpdateringstid
                    datafordelerRegisterImportSequenceNumber
                    datafordelerRowId
                    datafordelerRowVersion
                    ejerlejlighed
                    forretningshaendelse
                    forretningsomraade
                    forretningsproces
                    grund
                    husnummer
                    id_lokalId
                    id_namespace
                    jordstykke
                    kommunekode
                    registreringFra
                    registreringsaktoer
                    registreringTil
                    status
                    virkningFra
                    virkningsaktoer
                    virkningTil
                    husnummerBygning {
                        adgangsadressebetegnelse
                        adgangspunkt
                        adgangTilBygning
                        adgangTilTekniskAnlaeg
                        afstemningsomraade
                        datafordelerOpdateringstid
                        datafordelerRegisterImportSequenceNumber
                        datafordelerRowId
                        datafordelerRowVersion
                        forretningshaendelse
                        forretningsomraade
                        forretningsproces
                        geoDanmarkBygning
                        HusnummerHarAdgangspunkt {
                            datafordelerOpdateringstid
                            datafordelerRegisterImportSequenceNumber
                            datafordelerRowId
                            datafordelerRowVersion
                            forretningshaendelse
                            forretningsomraade
                            forretningsproces
                            id_lokalId
                            id_namespace
                            oprindelse_kilde
                            oprindelse_noejagtighedsklasse
                            oprindelse_registrering
                            oprindelse_tekniskStandard
                            position {
                                wkt
                                crs
                            }
                            registreringFra
                            registreringsaktoer
                            registreringTil
                            status
                            virkningFra
                            virkningsaktoer
                            virkningTil
                        }
                        husnummerretning {
                            wkt
                            crs
                        }
                        husnummertekst
                        id_lokalId
                        id_namespace
                        jordstykke
                        kommuneinddeling
                        menighedsraadsafstemningsomraade
                        navngivenVej
                        placeretPaaForeloebigtJordstykke
                        postnummer
                        registreringFra
                        registreringsaktoer
                        registreringTil
                        sogneinddeling
                        status
                        supplerendeBynavn
                        vejmidte
                        vejpunkt
                        virkningFra
                        virkningsaktoer
                        virkningTil
                    }

                }
                }
            }
        }

Bookmark: Demo 2 - query test
DAF2_GEODKV_Bygning_BBR_Bygning_DAR_Husnummer
    FetchIterations = 20
    FlexibleURL = https://graphql.datafordeler.dk/flexible/v1/
    fetchNumber = 200
    registreringstid = 20251202000000
    virkningstid = 20251202000000
    xmax = 555700
    xmin = 555240
    ymax = 6323000
    ymin = 6322550

Bookmark: Info
Note: Where clause / where: { / geometri: { / within: { / crs: 25832 / wkt: "POLYGON((@Value(query.xmin) @Value(query.ymin), @Value(query.xmin) @Value(query.ymax), @Value(query.xmax) @Value(query.ymax), @Value(query.xmax) @Value(query.ymin), @Value(query.xmin) @Value(query.ymin)))" / } / } / }
Note: Aalborg centrum vid Kongres & Kultur Center: / xmin 555240 / ymin 6322550 / xmax 555700 / ymax 6322900

FME custom transformer GraphQLtoJSON

Parameters:
- GQL =   # GraphQL

Input (input)
    -> Junction_19
Output (output)

Bookmark: 2.GraphQL string to JSON payload (secret sauce) 🕵
Junction_19
    -> ParameterFetcher
Note: Create _gql_rest attribute
ParameterFetcher
    ATTR_LIST = _gql $(GQL) _gql_rest $(GQL)
    -> StringReplacer
Note: Replace LF with \n
StringReplacer
    CASE = NO
    FIND_TEXT = "\n"
    NO_MATCH = _FME_NO_OP_
    REGEXP = NO
    REPLACE_TEXT = \n
    SRC_ATTRS = _gql_rest
    -> StringReplacer_2
StringReplacer_2
    CASE = NO
    FIND_TEXT = "
    NO_MATCH = _FME_NO_OP_
    REGEXP = NO
    REPLACE_TEXT = \"
    SRC_ATTRS = _gql_rest
    -> StringConcatenator
StringConcatenator
    ACTION = Create New Attribute
    PARM_LINE:
      fme_basicstring:22%17%22:{
        "query": "        @Value(_gql_rest)",
        "variables": {}
      }
    VAL_ATTR = _gql_rest
    -> Junction_20
Note: Escape " with \"
Note: Wrap in Json query and variables
Junction_20
    -> Junction
Junction
    -> Output (output)

FME custom transformer GraphQLtoJSON_2

Parameters:
- GQL =   # GraphQL

Input (input)
    -> Junction_19
Output (output)

Bookmark: 2.GraphQL string to JSON payload (secret sauce) 🕵
Junction_19
    -> ParameterFetcher
Note: Create _gql_rest attribute
ParameterFetcher
    ATTR_LIST = _gql $(GQL) _gql_rest $(GQL)
    -> StringReplacer
Note: Replace LF with \n
StringReplacer
    CASE = NO
    FIND_TEXT = "\n"
    NO_MATCH = _FME_NO_OP_
    REGEXP = NO
    REPLACE_TEXT = \n
    SRC_ATTRS = _gql_rest
    -> StringReplacer_2
StringReplacer_2
    CASE = NO
    FIND_TEXT = "
    NO_MATCH = _FME_NO_OP_
    REGEXP = NO
    REPLACE_TEXT = \"
    SRC_ATTRS = _gql_rest
    -> StringConcatenator
StringConcatenator
    ACTION = Create New Attribute
    PARM_LINE:
      fme_basicstring:22%17%22:{
        "query": "        @Value(_gql_rest)",
        "variables": {}
      }
    VAL_ATTR = _gql_rest
    -> Junction_20
Note: Escape " with \"
Note: Wrap in Json query and variables
Junction_20
    -> Junction
Junction
    -> Output (output)
