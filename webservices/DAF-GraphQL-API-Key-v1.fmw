FME workspace DAF-GraphQL-API-Key-v1.fmw

Parameters:
- DAF_CONNECTION = My DAF GraphQL API Key v1   # "DAF GraphQL API Key v1" Select a DAF GraphQL Web Connection
- GRAPHQL_QUERY:   # GraphQL Query
      query {
        DAR_Adressepunkt(
          first: 10,
          registreringstid: "2025-06-04T00:00:00Z"
          virkningstid:  "2025-06-04T00:00:00Z")
           {
          nodes {
            id_lokalId
            status
            oprindelse_kilde
            oprindelse_noejagtighedsklasse
            oprindelse_tekniskStandard
            position {
              wkt
              crs
              type
              dimension
            }
            registreringFra
            virkningFra
          }
        }
      }

Creator
    GEOMTYPE = Geometry Object
    NUM = 1
    CREATED -> JSONTemplater [ROOT]
JSONTemplater
    RESULT_ATTRIBUTE = _post_body
    ROOT_QUERY_EXPR:
      {
          "query": fme:get-attribute("_graphql.query"),
          "variables": {}
      }
    VISIBLE_QUERY_VALIDATE = Yes
    -> HTTPCaller
HTTPCaller
    AUTH_METHOD_TYPE = NC
    AUTH_NAMED_CONNECTION = $(DAF_CONNECTION)
    CLIENT_CERTIFICATE_TYPE = NONE
    CONNECTION_TIMEOUT_LENGTH = 60
    CONTENT_TYPE_LOOKUP = application/json
    ERROR_ATTR = _error
    FILE_PATH_ATTR = _response_file_path
    FOLLOW_REDIRECTS = FOLLOW_WITH_GET
    HTTP_METHOD = POST
    MAX_HTTP_VERSION = HTTP_2
    MAX_TRANSFERS_IN_PROGRESS = 25
    MINIMUM_ENCRYPTION_LEVEL = OS_DEFAULT
    OUTPUT_FILENAME = $(FME_MF_DIR)sample_response.json
    REDIRECT_AUTH = ORIGINAL_DOMAIN_ONLY
    RESPONSE_TYPE = File
    STATUS_CODE_ATTR = _http_status_code
    TARGET_URL = https://graphql.datafordeler.dk/DAR/v1
    TRANSFER_TIMEOUT_LENGTH = 90
    UPLOAD_BODY = @Value(_post_body)
    UPLOAD_TYPE = STRING_UPLOAD
    USE_COOKIES = No
    VERIFY_SSL_CERTIFICATES = Yes
    AUTH_METHOD = Web Connection
    UPLOAD_CONTENT_TYPE = JSON (application/json)
    -> FeatureReader [INITIATOR]
FeatureReader
    ATTR_ACCUM_MODE = Only Use Result
    COMBINE_GEOM = Use Result
    DATASET = @Value(_response_file_path)
    FORMAT = JSON
    INITIATOR_FIRST_OUTPUT = default
    JSON_DECODE_TEXT_STRINGS = Yes
    JSON_FEATURE_TYPE_KEY = json_featuretype
    JSON_FLATTEN_MODE = ONE_LEVEL
    JSON_GEOMETRY_FORMAT = None
    JSON_QUERY_TABLE = DAR_Adressepunkt json["data"]["DAR_Adressepunkt"]["nodes"][*]
    JSON_SAVE_FRAGMENTS = NO
    JSON_SCAN_MODE = QUERY
    JSON_USE_BASENAME_AS_DEFAULT_FEATURE_TYPE = No
    JSON_USE_SEARCH_ENVELOPE = NO
    ORDER_RESULTS = No
    OUTPUT_ADD_SCHEMA_ATTRIBUTES = NO
    OUTPUT_FEATURES_DISPLAY = Schema and Data Features
    <SCHEMA> -> FeatureReader__Schema_
    <OTHER> -> FeatureReader__Generic_ [off]
FeatureReader__Schema_: Logger
    LOG_FEATURE = LOG_ONLY
    MAXCOORDS = 20
    MAXFEATS = 20
    MESSAGE = Feature is:
    SEVERITY = INFO
FeatureReader__Generic_: Logger
    LOG_FEATURE = LOG_ONLY
    MAXCOORDS = 20
    MAXFEATS = 20
    MESSAGE = Feature is:
    SEVERITY = INFO
